# GardenPulse Traceability Specification
GardenPulse Unified Traceability Database

# Specification: GardenPulse Core Specification

## FEAT-001: Method-Agnostic Plant ID: (Feature)
Snap a leaf → AI detects plant + growing method + likely issues (deficiency, pest, overwatering)
- Status: Verified

## FEAT-002: Localized AI Agronomist: (Feature)
On-device machine learning evaluates leaf patterns against user-logged metrics and local climate data
- Status: Verified

## FEAT-003: Smart Weather Integration: (Feature)
Auto-adjusts care recommendations based on live forecast (e.g., "Rain tomorrow → skip watering today")
- Status: Verified

## FEAT-004: GPS/Network Location Detection: (Feature)
Enables hyper-local plant recommendations and regional pest/disease alerts
- Status: Verified

## FEAT-005: Auto Planting Zone Detection: (Feature)
USDA/Hardiness Zone auto-detect filters plant database to survivable species
- Status: Verified

## FEAT-006: Live Weather API Integration: (Feature)
OpenWeatherMap One Call API for real-time temp, humidity, precipitation, UV index
- Status: Verified

## FEAT-007: Local Community Features: (Feature)
Opt-in anonymized data shows what's thriving in your ZIP code right now
- Status: Verified

## FEAT-008: Smart Scheduler Engine: (Feature)
Auto-generates watering/feeding/light schedules based on your setup and local sunrise/sunset
- Status: Verified

## FEAT-009: Adaptive Reminders: (Feature)
Adjusts timing based on user behavior, weather forecasts, and seasonal changes
- Status: Verified

## FEAT-010: Date/Time Intelligence: (Feature)
Timezone-aware scheduling with daylight saving auto-adjust
- Status: Verified

## FEAT-011: Leaf Diagnostics Camera: (Feature)
On-device AI analyzes discoloration patterns without cloud upload
- Status: Verified

## FEAT-012: Progress Timelapse Generator: (Feature)
Auto-compiles photos into shareable growth reels with method-specific overlays
- Status: Verified

## FEAT-013: QR/Label Scanner: (Feature)
Scan nutrient bottles, seed packets, or sensor IDs for auto-logging
- Status: Verified

## FEAT-014: Accessibility Support: (Feature)
Voice commands critical for users with mobility challenges
- Status: Verified

## FEAT-015: Universal Recipe Calculator: (Feature)
Input any nutrient brand + water volume + growing method → precise dosing for soil drench, hydro reservoir, or foliar spray
- Status: Verified

## FEAT-016: Cemetery Log for Failed Grows: (Feature)
Historical log detailing causes of crop death (pH spikes, root rot) to spot patterns over time
- Status: Verified

## FEAT-017: One-Tap Quick Log: (Feature)
Photo + location tag + 1 slider = auto-logged entry with smart suggestions
- Status: Verified

## FEAT-018: Batch Mode: (Feature)
Log multiple plants across methods in minimal taps using smart defaults
- Status: Verified

## FEAT-019: Adaptive Growing Profiles: (Feature)
Toggle between "Low-Light Apartment", "Sunny Balcony", "Hydro Tent", "Raised Bed" → app adjusts all recommendations
- Status: Verified

## FEAT-020: Garden Health Score™: (Feature)
Tracks 8 metrics (soil moisture trend, light exposure, pH stability, growth rate) with plain-English insights
- Status: Verified

## FEAT-021: Cross-Method Insights: (Feature)
e.g., "Your hydro basil grew 20% faster than soil → try adjusting nutrient strength for soil batch"
- Status: Planned

## FEAT-022: Confidence Score™ (Optional): (Feature)
Tracks mastery across 15 method-agnostic skills for learners
- Status: Planned

## FEAT-023: High-Intent Interstitials: (Feature)
Triggered at calculation/export moments ($25–45 eCPM in Tier 1)
- Status: Planned

## FEAT-024: Contextual Native Ads: (Feature)
Styled as "Garden Tips" or "Tool Recommendations" in timeline
- Status: Planned

## FEAT-025: Rewarded Videos: (Feature)
Unlock premium exports (PDF garden plans, compliance logs), advanced calculators
- Status: Planned

## FEAT-026: Geo-Targeted Local Ads: (Feature)
Partner with local nurseries, garden centers for hyper-relevant promotions (opt-in)
- Status: Planned

## FEAT-027: Optional Supporter Badge: (Feature)
$2.99 one-time to remove only interstitials (preserves native ad revenue)
- Status: Planned

## FEAT-028: Local Grow Maps: (Feature)
Opt-in anonymized data shows regional success patterns (e.g., "Cherry tomatoes succeeding in 87% of Berlin balconies")
- Status: Planned

## FEAT-029: Garden Clusters: (Feature)
Join location or interest-based groups to share tips, swap seeds, compare progress
- Status: Planned

## FEAT-030: Growth Streaks + Method Badges: (Feature)
Unlock "Hydro Master", "Balcony Boss", "Zero-Waste Gardener" via consistent logging
- Status: Planned

## FEAT-031: Shareable Progress Reels: (Feature)
Auto-generated "Before/After" timelapses and "My Garden Setup" infographics for Instagram/TikTok
- Status: Planned

## FEAT-032: Contextual In-App Articles: (Feature)
Content appears when users log related actions (e.g., log "yellow leaves" → suggest "Magnesium Deficiency Guide")
- Status: Planned

## FEAT-033: Offline-First Caching: (Feature)
Download articles on Wi-Fi → available offline (aligns with privacy/offline USP)
- Status: Planned

## FEAT-034: Method-Specific Guides: (Feature)
e.g., "Container Tomatoes in Small Spaces", "Berlin Balcony Prep: March", "Hydro Starter Checklist"
- Status: Planned

## FEAT-035: Creator Studio (Opt-In): (Feature)
Allow expert gardeners to publish guides → earn revenue share from AdMob ads in their posts
- Status: Planned

## FEAT-036: User-Controlled Delivery: (Feature)
Toggle "Show learning tips" in settings; never auto-play videos or interrupt core workflows
- Status: Planned

## REQ-001: FR-SYS-001 (Requirement)
The system shall NOT require user registration, account creation, or sign-in to access any core feature. The app shall open directly to the Dashboard (returning users) or Onboarding (first-time launch).
- Status: Verified
- fulfills -> FEAT-019
- fulfills -> FEAT-033

## REQ-002: FR-SYS-002 (Requirement)
The system shall operate fully offline for all features that do not inherently require a network connection (plant logging, schedule viewing, tip reading from cache, diagnostics, calculator).
- Status: Verified
- fulfills -> FEAT-019
- fulfills -> FEAT-033

## REQ-003: FR-SYS-003 (Requirement)
When operating offline, the system shall display a non-blocking indicator informing the user that weather data and community features require a connection, without preventing access to offline-capable features.
- Status: Verified
- fulfills -> FEAT-019
- fulfills -> FEAT-033

## REQ-004: FR-SYS-004 (Requirement)
The system shall store the user's primary growing method selection and apply it as the default context across all screens, recommendations, tips, and ad targeting throughout the app.
- Status: Verified
- fulfills -> FEAT-019

## REQ-005: FR-SYS-005 (Requirement)
The system shall support all four growing methods simultaneously. A user may have plants of different methods active at the same time, and the system shall apply method-specific logic independently per plant.
- Status: Verified
- fulfills -> FEAT-019

## REQ-006: FR-SYS-006 (Requirement)
When displaying care recommendations, tips, or calculator results, the system shall filter and tailor content to the growing method of the plant or context in question.
- Status: Verified
- fulfills -> FEAT-019

## REQ-007: FR-SYS-007 (Requirement)
The system shall cache the user's zone and the 7-day weather forecast locally upon each successful API response. Cached data shall be used when the device is offline or the API call fails.
- Status: Verified
- fulfills -> FEAT-004
- fulfills -> FEAT-005
- fulfills -> FEAT-006

## REQ-008: FR-SYS-008 (Requirement)
The system shall refresh the cached weather data upon each app open if a network connection is available, and upon user-triggered pull-to-refresh.
- Status: Verified
- fulfills -> FEAT-004
- fulfills -> FEAT-005
- fulfills -> FEAT-006

## REQ-009: FR-SYS-009 (Requirement)
If the user declines location permission, the system shall provide a manual ZIP/postal code entry fallback and derive zone and weather data from that entry.
- Status: Verified
- fulfills -> FEAT-004
- fulfills -> FEAT-005
- fulfills -> FEAT-006

## REQ-010: FR-SYS-010 (Requirement)
The system shall never display a user's precise GPS coordinates anywhere in the app UI or share them with community features. All location data used in community and map features shall be anonymized to zone or city level.
- Status: Verified
- fulfills -> FEAT-004
- fulfills -> FEAT-005
- fulfills -> FEAT-006

## REQ-011: FR-SYS-011 (Requirement)
The system shall send care reminder notifications only for plant tasks that are due or overdue, referencing the specific plant name and task type (e.g., "Your balcony tomatoes need water in 2 days based on local forecast").
- Status: Verified
- fulfills -> FEAT-009

## REQ-012: FR-SYS-012 (Requirement)
The system shall automatically adjust scheduled notification times based on detected weather conditions (e.g., suppress a watering reminder on a day forecast to have rain above 70% probability).
- Status: Verified
- fulfills -> FEAT-009

## REQ-013: FR-SYS-013 (Requirement)
The system shall support timezone-aware scheduling and shall automatically adjust reminder times when the device timezone changes or daylight saving time transitions occur.
- Status: Verified
- fulfills -> FEAT-009

## REQ-014: FR-SYS-014 (Requirement)
The system shall NEVER display any advertisement (interstitial, rewarded, or native) on any permission request screen (MOD-04) or during the onboarding flow (ONB-1 through ONB-4).
- Status: Verified
- fulfills -> FEAT-023
- fulfills -> FEAT-024
- fulfills -> FEAT-025
- fulfills -> FEAT-027

## REQ-015: FR-SYS-015 (Requirement)
The system shall geo-fence ad categories restricted by local law (e.g., cannabis-adjacent products) based on the user's detected or manually entered location.
- Status: Verified
- fulfills -> FEAT-023
- fulfills -> FEAT-024
- fulfills -> FEAT-025
- fulfills -> FEAT-027

## REQ-016: FR-SYS-016 (Requirement)
The system shall ensure that rewarded videos are always optional and clearly labelled as an exchange ("Watch a video to unlock [X]"). The user shall be able to decline without losing access to core functionality.
- Status: Verified
- fulfills -> FEAT-023
- fulfills -> FEAT-024
- fulfills -> FEAT-025
- fulfills -> FEAT-027

## REQ-017: FR-SYS-017 (Requirement)
When a user has purchased the Supporter Badge, the system shall permanently suppress all interstitial ad (MOD-06) triggers for that user. Native ads shall continue to appear.
- Status: Verified
- fulfills -> FEAT-023
- fulfills -> FEAT-024
- fulfills -> FEAT-025
- fulfills -> FEAT-027

## REQ-018: FR-SYS-018 (Requirement)
The system shall never upload photos taken in Leaf Diagnostics (SCR-06) to any external server. All image analysis shall occur on-device.
- Status: Verified
- fulfills -> FEAT-011
- fulfills -> FEAT-014

## REQ-019: FR-SYS-019 (Requirement)
The system shall provide a one-tap path to delete all user data from within the Privacy Dashboard (SCR-13), compliant with GDPR right to erasure and CCPA deletion rights.
- Status: Verified
- fulfills -> FEAT-011
- fulfills -> FEAT-014

## REQ-020: FR-SYS-020 (Requirement)
The system shall declare all permissions (location, camera, microphone) in the platform manifest (Info.plist / AndroidManifest.xml) with clear purpose strings explaining the benefit to the user.
- Status: Verified
- fulfills -> FEAT-011
- fulfills -> FEAT-014

## REQ-021: FR-SYS-021 (Requirement)
The system shall request camera and microphone permissions contextually — only when the user taps a feature that requires them — and never at app launch or during onboarding unless the user actively initiates a camera or mic action.
- Status: Verified
- fulfills -> FEAT-011
- fulfills -> FEAT-014

## REQ-022: FR-SYS-022 (Requirement)
The system shall support full VoiceOver (iOS) and TalkBack (Android) compatibility for all interactive elements across all screens.
- Status: Verified
- fulfills -> FEAT-014

## REQ-023: FR-SYS-023 (Requirement)
The system shall auto-detect the device's regional locale to set the default unit system (metric vs. imperial) and shall provide a manual override in Settings (SCR-12).
- Status: Verified
- fulfills -> FEAT-014

## REQ-024: FR-SYS-024 (Requirement)
The system shall support at minimum two languages at launch: English and German. Additional languages (French, Spanish, Dutch) shall be supported as localization is completed.
- Status: Verified
- fulfills -> FEAT-014

## REQ-025: FR-ONB1-001 (Requirement)
The system shall display the Splash Screen as the first screen when the app is launched for the first time on a device.
- Status: Verified
- fulfills -> FEAT-019

## REQ-026: FR-ONB1-002 (Requirement)
When a returning user launches the app (i.e., they have previously completed onboarding), the system shall skip ONB-1 through ONB-4 and navigate directly to SCR-01 Dashboard.
- Status: Verified
- fulfills -> FEAT-019

## REQ-027: FR-ONB1-003 (Requirement)
The Splash Screen shall auto-advance to ONB-2 (Welcome + Method Selection) after initialization completes without requiring any user interaction.
- Status: Verified
- fulfills -> FEAT-019

## REQ-028: FR-ONB1-004 (Requirement)
The system shall display the GardenPulse app logo with an animated leaf-unfurl entry animation.
- Status: Verified
- fulfills -> FEAT-019

## REQ-029: FR-ONB1-005 (Requirement)
The system shall display the app name "GardenPulse" and the tagline "Grow Smarter, Anywhere." on the Splash Screen.
- Status: Verified
- fulfills -> FEAT-019

## REQ-030: FR-ONB1-006 (Requirement)
The system shall display a subtle animated loading indicator (pulse animation) during the 2-second display period.
- Status: Verified
- fulfills -> FEAT-019

## REQ-031: FR-ONB1-007 (Requirement)
The Splash Screen shall not display any advertisement, sign-in prompt, or permission request.
- Status: Verified
- fulfills -> FEAT-019

## REQ-032: FR-ONB2-001 (Requirement)
The system shall navigate to ONB-2 automatically after ONB-1 completes.
- Status: Verified
- fulfills -> FEAT-019

## REQ-033: FR-ONB2-002 (Requirement)
When the user taps "Skip for now," the system shall record no method selection, set all growing method preferences to "All," and proceed to ONB-3.
- Status: Verified
- fulfills -> FEAT-019

## REQ-034: FR-ONB2-003 (Requirement)
When the user taps "Next" and method selection is complete, the system shall trigger MOD-04 (Permission Context Modal — Location) before navigating to ONB-3.
- Status: Verified
- fulfills -> FEAT-019

## REQ-035: FR-ONB2-004 (Requirement)
The system shall display a 3-step progress indicator at the top of the screen, with Step 1 of 3 active.
- Status: Verified
- fulfills -> FEAT-019

## REQ-036: FR-ONB2-005 (Requirement)
The system shall display four selectable method cards: Soil / Raised Bed, Container / Balcony, Hydroponic, and Indoor Plants. Each card shall show a distinct icon, method name, and a one-line description.
- Status: Verified
- fulfills -> FEAT-019

## REQ-037: FR-ONB2-006 (Requirement)
The "Next →" button shall be disabled (visually greyed) until the user selects at least one method card.
- Status: Verified
- fulfills -> FEAT-019

## REQ-038: FR-ONB2-007 (Requirement)
When the user taps a method card, the system shall visually highlight it with a selection ring and enable the "Next →" button.
- Status: Verified
- fulfills -> FEAT-019

## REQ-039: FR-ONB2-008 (Requirement)
The method selection shall be single-select. Tapping a second card shall deselect the first and select the new one.
- Status: Verified
- fulfills -> FEAT-019

## REQ-040: FR-ONB2-009 (Requirement)
The system shall store the selected growing method as the user's primary growing profile preference, which will pre-fill method selectors throughout the app.
- Status: Verified
- fulfills -> FEAT-019

## REQ-041: FR-ONB2-010 (Requirement)
The system shall NOT display any advertisement on this screen.
- Status: Verified
- fulfills -> FEAT-019

## REQ-042: FR-ONB3-001 (Requirement)
The system shall navigate to ONB-3 after the location permission step (MOD-04) completes — whether the user grants, denies, or dismisses the permission.
- Status: Verified
- fulfills -> FEAT-019

## REQ-043: FR-ONB3-002 (Requirement)
When the user taps "Skip for now," the system shall navigate directly to ONB-4 with the plant data fields empty, resulting in a generic care plan preview.
- Status: Verified
- fulfills -> FEAT-019

## REQ-044: FR-ONB3-003 (Requirement)
The system shall display a Back arrow that returns the user to ONB-2 without losing their method selection.
- Status: Verified
- fulfills -> FEAT-019

## REQ-045: FR-ONB3-004 (Requirement)
The system shall display a 3-step progress indicator with Step 2 of 3 active.
- Status: Verified
- fulfills -> FEAT-019

## REQ-046: FR-ONB3-005 (Requirement)
The system shall display a plant name search field with an autocomplete dropdown sourced from the app's local plant database (minimum 3,000 species entries).
- Status: Verified
- fulfills -> FEAT-019

## REQ-047: FR-ONB3-006 (Requirement)
The system shall display browse-by-category chips: Herb, Vegetable, Fruit, Flower, Houseplant, Microgreen. Tapping a chip shall filter the autocomplete suggestions.
- Status: Verified
- fulfills -> FEAT-019

## REQ-048: FR-ONB3-007 (Requirement)
When a plant is selected from search or browse, the system shall display a preview card showing: plant thumbnail, common name, scientific name, and a method compatibility badge relative to the method selected in ONB-2.
- Status: Verified
- fulfills -> FEAT-019

## REQ-049: FR-ONB3-008 (Requirement)
The system shall display the growing method selector pills (Soil · Container · Hydro · Indoor) pre-filled with the method chosen in ONB-2, and allow the user to change the selection for this specific plant.
- Status: Verified
- fulfills -> FEAT-019

## REQ-050: FR-ONB3-009 (Requirement)
The system shall display the auto-detected or manually entered location as a zone badge (e.g., "Zone 7b · Berlin"). If location was declined in MOD-04 and no manual entry was made, the zone badge shall display "Zone unknown — set in Settings."
- Status: Verified
- fulfills -> FEAT-019

## REQ-051: FR-ONB3-010 (Requirement)
The system shall display a started date picker defaulting to the current date.
- Status: Verified
- fulfills -> FEAT-019

## REQ-052: FR-ONB3-011 (Requirement)
The plant nickname field shall accept a maximum of 30 characters.
- Status: Verified
- fulfills -> FEAT-019

## REQ-053: FR-ONB3-012 (Requirement)
When the user taps the "Scan a leaf or seed packet" camera button, the system shall trigger MOD-04 (Permission Context Modal — Camera) if camera permission has not been granted, and then open MOD-03 (QR Scanner Overlay) for seed packet scanning or MOD-02 (Add / Edit Plant Sheet) pre-filled with camera scan data.
- Status: Verified
- fulfills -> FEAT-019

## REQ-054: FR-ONB3-013 (Requirement)
The "Continue →" button shall be enabled only when a plant name (from search, browse, or manual entry) is present. All other fields are optional.
- Status: Verified
- fulfills -> FEAT-019

## REQ-055: FR-ONB3-014 (Requirement)
Upon tapping "Continue →," the system shall persist the plant record with: species name, nickname (if provided), growing method, zone, started date, and a reference to the user's primary growing profile.
- Status: Verified
- fulfills -> FEAT-019

## REQ-056: FR-ONB4-001 (Requirement)
The system shall navigate to ONB-4 after ONB-3's Continue action or Skip action completes.
- Status: Verified
- fulfills -> FEAT-019

## REQ-057: FR-ONB4-002 (Requirement)
When the user taps "Start Growing 🌱," the system shall mark onboarding as complete, persist this flag to local storage, and navigate to SCR-01 Dashboard.
- Status: Verified
- fulfills -> FEAT-019

## REQ-058: FR-ONB4-003 (Requirement)
The system shall display a Back arrow that returns the user to ONB-3 without losing the plant data entered.
- Status: Verified
- fulfills -> FEAT-019

## REQ-059: FR-ONB4-004 (Requirement)
When the user taps "Remind me later," the system shall navigate to SCR-01 Dashboard without requesting notification permission.
- Status: Verified
- fulfills -> FEAT-019

## REQ-060: FR-ONB4-005 (Requirement)
The system shall display a 3-step progress indicator with Step 3 of 3 active.
- Status: Verified
- fulfills -> FEAT-019

## REQ-061: FR-ONB4-006 (Requirement)
The system shall display a location and weather context card showing: detected city name, zone badge, current temperature, current humidity, and a weather forecast icon. If weather data is unavailable, the card shall display "Weather loading…" and retry in background.
- Status: Verified
- fulfills -> FEAT-019

## REQ-062: FR-ONB4-007 (Requirement)
If a plant was added in ONB-3, the system shall display a personalised first plant care summary card containing: watering frequency recommendation, light requirement badge, next recommended action chip (e.g., "Water today"), and the plant's growing method tag. All values shall be derived from the plant's species data and the user's zone.
- Status: Verified
- fulfills -> FEAT-019

## REQ-063: FR-ONB4-008 (Requirement)
If no plant was added in ONB-3 (user skipped), the system shall display a generic care tip card based on the selected growing method instead of a plant-specific card.
- Status: Verified
- fulfills -> FEAT-019

## REQ-064: FR-ONB4-009 (Requirement)
The system shall display a Garden Health Score baseline card with a circular dial showing an initial score of 50/100 and the label "We'll track your progress from here."
- Status: Verified
- fulfills -> FEAT-019

## REQ-065: FR-ONB4-010 (Requirement)
The system shall display a notification opt-in row: bell icon, label "Get reminders for your [plant name]" (or "Get growing reminders" if no plant was added), and an Enable toggle.
- Status: Verified
- fulfills -> FEAT-019

## REQ-066: FR-ONB4-011 (Requirement)
When the user taps the Enable notification toggle, the system shall trigger MOD-04 (Permission Context Modal — Notifications) before requesting the OS notification permission.
- Status: Verified
- fulfills -> FEAT-019

## REQ-067: FR-ONB4-012 (Requirement)
The system shall NOT display any advertisement on this screen.
- Status: Verified
- fulfills -> FEAT-019

## REQ-068: FR-S01-001 (Requirement)
The system shall display the Dashboard as the default screen when the main app is entered for the first time (after onboarding) and as the Home tab in the bottom navigation bar.
- Status: Verified
- fulfills -> FEAT-020
- fulfills -> FEAT-006
- fulfills -> FEAT-009
- fulfills -> FEAT-024
- fulfills -> FEAT-003

## REQ-069: FR-S01-002 (Requirement)
When a returning user opens the app after a lapse, the system shall display a Comeback Bonus banner on the Dashboard: a dismissible card reading "Welcome back! Your [plant name] missed you" (or "Welcome back!" if no plants exist), with the plant's health change since last visit.
- Status: Verified
- fulfills -> FEAT-020
- fulfills -> FEAT-006
- fulfills -> FEAT-009
- fulfills -> FEAT-024
- fulfills -> FEAT-003

## REQ-070: FR-S01-003 (Requirement)
Tapping the Settings icon in the header shall navigate to SCR-12 Settings.
- Status: Verified
- fulfills -> FEAT-020
- fulfills -> FEAT-006
- fulfills -> FEAT-009
- fulfills -> FEAT-024
- fulfills -> FEAT-003

## REQ-071: FR-S01-004 (Requirement)
Tapping the notification bell icon shall display an in-app notification tray. The bell shall show a badge count when unread notifications are present.
- Status: Verified
- fulfills -> FEAT-020
- fulfills -> FEAT-006
- fulfills -> FEAT-009
- fulfills -> FEAT-024
- fulfills -> FEAT-003

## REQ-072: FR-S01-005 (Requirement)
The system shall display the user's city name and zone badge (e.g., "Berlin · Zone 7b") in the weather widget header.
- Status: Verified
- fulfills -> FEAT-020
- fulfills -> FEAT-006
- fulfills -> FEAT-009
- fulfills -> FEAT-024
- fulfills -> FEAT-003

## REQ-073: FR-S01-006 (Requirement)
The system shall display the following real-time weather values in the widget: current temperature, humidity percentage, UV index, and rain probability for today. Data shall be sourced from the OpenWeatherMap One Call API.
- Status: Verified
- fulfills -> FEAT-020
- fulfills -> FEAT-006
- fulfills -> FEAT-009
- fulfills -> FEAT-024
- fulfills -> FEAT-003

## REQ-074: FR-S01-007 (Requirement)
The system shall display a 3-day forecast strip beneath the main weather values, showing a weather icon and high/low temperature for each of the next 3 days.
- Status: Verified
- fulfills -> FEAT-020
- fulfills -> FEAT-006
- fulfills -> FEAT-009
- fulfills -> FEAT-024
- fulfills -> FEAT-003

## REQ-075: FR-S01-008 (Requirement)
When tomorrow's rain probability is ≥70%, the system shall display a contextual smart alert label within the weather widget: "[Plant name] watering → may skip tomorrow due to rain forecast." If multiple plants are affected, the system shall show a summary "X plants may not need watering tomorrow."
- Status: Verified
- fulfills -> FEAT-020
- fulfills -> FEAT-006
- fulfills -> FEAT-009
- fulfills -> FEAT-024
- fulfills -> FEAT-003

## REQ-076: FR-S01-009 (Requirement)
The weather widget shall support pull-to-refresh. When triggered, the system shall request a fresh weather API call and update all weather values if a network connection is available.
- Status: Verified
- fulfills -> FEAT-020
- fulfills -> FEAT-006
- fulfills -> FEAT-009
- fulfills -> FEAT-024
- fulfills -> FEAT-003

## REQ-077: FR-S01-010 (Requirement)
When weather data is unavailable (offline and no cache), the system shall display the last cached values with a "Last updated [time]" label and a "Reconnect to refresh" note.
- Status: Verified
- fulfills -> FEAT-020
- fulfills -> FEAT-006
- fulfills -> FEAT-009
- fulfills -> FEAT-024
- fulfills -> FEAT-003

## REQ-078: FR-S01-011 (Requirement)
The system shall display a "Today in Your Garden" section containing horizontally scrollable task cards for all plants with tasks due today.
- Status: Verified
- fulfills -> FEAT-020
- fulfills -> FEAT-006
- fulfills -> FEAT-009
- fulfills -> FEAT-024
- fulfills -> FEAT-003

## REQ-079: FR-S01-012 (Requirement)
Each task card shall display: the plant's thumbnail photo, plant name, and task type chip (Water / Feed / Prune / Check / Harvest). The task type shall be determined by the plant's care schedule in SCR-07.
- Status: Verified
- fulfills -> FEAT-020
- fulfills -> FEAT-006
- fulfills -> FEAT-009
- fulfills -> FEAT-024
- fulfills -> FEAT-003

## REQ-080: FR-S01-013 (Requirement)
Each task card shall include a "Done ✓" button. When tapped, the system shall mark the task as complete for the current day, update the plant's log, dismiss the card from the today list, and animate the card out.
- Status: Verified
- fulfills -> FEAT-020
- fulfills -> FEAT-006
- fulfills -> FEAT-009
- fulfills -> FEAT-024
- fulfills -> FEAT-003

## REQ-081: FR-S01-014 (Requirement)
When all tasks for the day are marked complete, the system shall display an animated celebration state ("All done today! 🎉") in place of the task list for the remainder of the day.
- Status: Verified
- fulfills -> FEAT-020
- fulfills -> FEAT-006
- fulfills -> FEAT-009
- fulfills -> FEAT-024
- fulfills -> FEAT-003

## REQ-082: FR-S01-015 (Requirement)
The system shall display a "See full schedule →" link in this section that navigates to SCR-07 Smart Scheduler.
- Status: Verified
- fulfills -> FEAT-020
- fulfills -> FEAT-006
- fulfills -> FEAT-009
- fulfills -> FEAT-024
- fulfills -> FEAT-003

## REQ-083: FR-S01-016 (Requirement)
Weather-adjusted tasks (e.g., watering suppressed due to rain forecast) shall display as greyed-out with a weather icon and the label "Skipped — rain forecast" rather than being removed from the list entirely.
- Status: Verified
- fulfills -> FEAT-020
- fulfills -> FEAT-006
- fulfills -> FEAT-009
- fulfills -> FEAT-024
- fulfills -> FEAT-003

## REQ-084: FR-S01-017 (Requirement)
The system shall display the overall Garden Health Score as a circular dial (0–100) with colour coding: 0–33 red, 34–66 amber, 67–100 green.
- Status: Verified
- fulfills -> FEAT-020
- fulfills -> FEAT-006
- fulfills -> FEAT-009
- fulfills -> FEAT-024
- fulfills -> FEAT-003

## REQ-085: FR-S01-018 (Requirement)
The system shall display the 3 most impactful metric labels beneath the dial (e.g., "Moisture · Light · pH"), derived from the lowest-scoring metrics across all the user's active plants.
- Status: Verified
- fulfills -> FEAT-020
- fulfills -> FEAT-006
- fulfills -> FEAT-009
- fulfills -> FEAT-024
- fulfills -> FEAT-003

## REQ-086: FR-S01-019 (Requirement)
Tapping "View Details →" on the Garden Health Score card shall navigate to SCR-11 Profile & Badges.
- Status: Verified
- fulfills -> FEAT-020
- fulfills -> FEAT-006
- fulfills -> FEAT-009
- fulfills -> FEAT-024
- fulfills -> FEAT-003

## REQ-087: FR-S01-020 (Requirement)
The system shall display a horizontally scrollable row of the user's plants, each shown as a thumbnail card with: plant photo, plant name, and a health dot indicator (green/amber/red).
- Status: Verified
- fulfills -> FEAT-020
- fulfills -> FEAT-006
- fulfills -> FEAT-009
- fulfills -> FEAT-024
- fulfills -> FEAT-003

## REQ-088: FR-S01-021 (Requirement)
Tapping a plant card in the My Plants row shall navigate to SCR-03 Plant Detail for that plant.
- Status: Verified
- fulfills -> FEAT-020
- fulfills -> FEAT-006
- fulfills -> FEAT-009
- fulfills -> FEAT-024
- fulfills -> FEAT-003

## REQ-089: FR-S01-022 (Requirement)
Tapping "See All →" shall navigate to SCR-02 Plant List.
- Status: Verified
- fulfills -> FEAT-020
- fulfills -> FEAT-006
- fulfills -> FEAT-009
- fulfills -> FEAT-024
- fulfills -> FEAT-003

## REQ-090: FR-S01-023 (Requirement)
If the user has no plants, the My Plants row shall be replaced by a "Add your first plant" empty-state card that triggers MOD-02 on tap.
- Status: Verified
- fulfills -> FEAT-020
- fulfills -> FEAT-006
- fulfills -> FEAT-009
- fulfills -> FEAT-024
- fulfills -> FEAT-003

## REQ-091: FR-S01-024 (Requirement)
The system shall display at most one contextual tip card per Dashboard session. The tip shall be selected based on the user's most recently logged action or the current season and zone.
- Status: Verified
- fulfills -> FEAT-020
- fulfills -> FEAT-006
- fulfills -> FEAT-009
- fulfills -> FEAT-024
- fulfills -> FEAT-003

## REQ-092: FR-S01-025 (Requirement)
The tip card shall display: the label "From your garden expert," the article title, method tag, and estimated read time. Tapping the card shall open MOD-09 Tip Article Reader Sheet.
- Status: Verified
- fulfills -> FEAT-020
- fulfills -> FEAT-006
- fulfills -> FEAT-009
- fulfills -> FEAT-024
- fulfills -> FEAT-003

## REQ-093: FR-S01-026 (Requirement)
The tip card shall only display content from the offline-cached Smart Tips Library. The system shall not load external webviews for tip content.
- Status: Verified
- fulfills -> FEAT-020
- fulfills -> FEAT-006
- fulfills -> FEAT-009
- fulfills -> FEAT-024
- fulfills -> FEAT-003

## REQ-094: FR-S01-027 (Requirement)
The contextual tip card shall NOT auto-play any video or audio.
- Status: Verified
- fulfills -> FEAT-020
- fulfills -> FEAT-006
- fulfills -> FEAT-009
- fulfills -> FEAT-024
- fulfills -> FEAT-003

## REQ-095: FR-S01-028 (Requirement)
On Monday mornings, or when the user opens the app for the first time after a lapse with at least one week of log data, the system shall display the Weekly Bloom Report banner with a "Your weekly report is ready 📊" label and a "View Report" button.
- Status: Verified
- fulfills -> FEAT-020
- fulfills -> FEAT-006
- fulfills -> FEAT-009
- fulfills -> FEAT-024
- fulfills -> FEAT-003

## REQ-096: FR-S01-029 (Requirement)
Tapping "View Report" on the banner shall open MOD-11 Weekly Bloom Report Sheet.
- Status: Verified
- fulfills -> FEAT-020
- fulfills -> FEAT-006
- fulfills -> FEAT-009
- fulfills -> FEAT-024
- fulfills -> FEAT-003

## REQ-097: FR-S01-030 (Requirement)
The system shall display one native ad slot on the Dashboard, positioned between the Garden Health Score card and the My Plants row. The ad shall be styled to match surrounding content cards.
- Status: Verified
- fulfills -> FEAT-020
- fulfills -> FEAT-006
- fulfills -> FEAT-009
- fulfills -> FEAT-024
- fulfills -> FEAT-003

## REQ-098: FR-S01-031 (Requirement)
The system shall display a prominent "+" floating action button (FAB) in the bottom-right corner, always visible above the bottom navigation bar. Tapping it shall open MOD-01 Quick Log Sheet.
- Status: Verified
- fulfills -> FEAT-020
- fulfills -> FEAT-006
- fulfills -> FEAT-009
- fulfills -> FEAT-024
- fulfills -> FEAT-003

## REQ-099: FR-S02-001 (Requirement)
The system shall display the Plant List when the user taps the Garden tab in the bottom navigation bar.
- Status: Verified
- fulfills -> FEAT-017
- fulfills -> FEAT-018

## REQ-100: FR-S02-002 (Requirement)
Tapping a plant card shall navigate to SCR-03 Plant Detail for that plant.
- Status: Verified
- fulfills -> FEAT-017
- fulfills -> FEAT-018

## REQ-101: FR-S02-003 (Requirement)
Tapping the "+" icon in the header shall open MOD-02 Add / Edit Plant Sheet.
- Status: Planned
- fulfills -> FEAT-017
- fulfills -> FEAT-018

## REQ-102: FR-S02-004 (Requirement)
The system shall display all of the user's active (non-archived) plants as cards. The default view shall be a 2-column grid; a list view shall be available via a toggle icon.
- Status: Planned
- fulfills -> FEAT-017
- fulfills -> FEAT-018

## REQ-103: FR-S02-005 (Requirement)
Each plant card shall display: plant photo thumbnail, plant name (common name + nickname if set), growing method badge, a health dot indicator (green/amber/red based on Garden Health Score), and a "Last logged X days ago" label.
- Status: Planned
- fulfills -> FEAT-017
- fulfills -> FEAT-018

## REQ-104: FR-S02-006 (Requirement)
The system shall display growing method filter chips (All · Soil · Container · Hydro · Indoor) above the list. Tapping a chip shall filter the visible plants to only those matching the selected method.
- Status: Planned
- fulfills -> FEAT-017
- fulfills -> FEAT-018

## REQ-105: FR-S02-007 (Requirement)
The system shall display a search field above the plant cards. As the user types, the system shall filter the visible plant list in real time to match by plant name or nickname.
- Status: Planned
- fulfills -> FEAT-017
- fulfills -> FEAT-018

## REQ-106: FR-S02-008 (Requirement)
The system shall display a sort control allowing the user to sort plants by: name (A–Z), health score (lowest first), growing method, or last logged date.
- Status: Planned
- fulfills -> FEAT-017
- fulfills -> FEAT-018

## REQ-107: FR-S02-009 (Requirement)
When the user has no plants, the system shall display an empty state with an illustrated pot graphic, the heading "No plants yet," and an "Add Your First Plant" button that opens MOD-02.
- Status: Planned
- fulfills -> FEAT-017
- fulfills -> FEAT-018

## REQ-108: FR-S02-010 (Requirement)
A native ad card shall appear in the plant list at approximately every 10th item position when the user has more than 10 plants.
- Status: Planned
- fulfills -> FEAT-017
- fulfills -> FEAT-018

## REQ-109: FR-S02-011 (Requirement)
The system shall support a swipe-left gesture on each plant card. The revealed actions shall be: "Quick Log" (opens MOD-01 pre-filled for that plant) and "Archive" (triggers a confirmation dialog before moving the plant to SCR-14 Cemetery Log).
- Status: Planned
- fulfills -> FEAT-017
- fulfills -> FEAT-018

## REQ-110: FR-S02-012 (Requirement)
The system shall support pull-to-refresh to re-sync plant health data.
- Status: Planned
- fulfills -> FEAT-017
- fulfills -> FEAT-018

## REQ-111: FR-S02-013 (Requirement)
The system shall provide a batch mode toggle in the header. When activated, all plant cards shall show multi-select checkboxes.
- Status: Planned
- fulfills -> FEAT-017
- fulfills -> FEAT-018

## REQ-112: FR-S02-014 (Requirement)
When batch mode is active, the system shall display a "Select All" button in the header that selects all visible (filtered) plants.
- Status: Planned
- fulfills -> FEAT-017
- fulfills -> FEAT-018

## REQ-113: FR-S02-015 (Requirement)
When one or more plants are selected in batch mode, the system shall display an action bar at the bottom of the screen with the actions: Water All, Feed All, Log Entry, and Archive. These actions shall trigger MOD-08 Batch Mode Overlay.
- Status: Planned
- fulfills -> FEAT-017
- fulfills -> FEAT-018

## REQ-114: FR-S02-016 (Requirement)
Before executing any batch action, the system shall display a confirmation dialog: "Apply [action] to [N] plants?" with Confirm and Cancel options.
- Status: Planned
- fulfills -> FEAT-017
- fulfills -> FEAT-018

## REQ-115: FR-S02-017 (Requirement)
Tapping "Cancel" or the batch mode toggle again shall exit batch mode without performing any action and restore the normal plant card view.
- Status: Planned
- fulfills -> FEAT-017
- fulfills -> FEAT-018

## REQ-116: FR-S02-018 (Requirement)
The system shall display a "+" FAB (bottom-right) at all times in the Plant List. Tapping it shall open MOD-01 Quick Log Sheet.
- Status: Planned
- fulfills -> FEAT-017
- fulfills -> FEAT-018

## REQ-117: FR-S03-001 (Requirement)
The system shall display Plant Detail when the user taps a plant card from SCR-02 or a plant card from SCR-01 Dashboard.
- Status: Planned
- fulfills -> FEAT-017
- fulfills -> FEAT-021

## REQ-118: FR-S03-002 (Requirement)
The header shall display the plant's name and a back arrow returning to the previous screen.
- Status: Planned
- fulfills -> FEAT-017
- fulfills -> FEAT-021

## REQ-119: FR-S03-003 (Requirement)
The overflow menu (⋮) in the header shall offer: Edit Plant (opens MOD-02 pre-filled), Archive to Cemetery (with confirmation dialog), and Delete (with destructive confirmation dialog).
- Status: Planned
- fulfills -> FEAT-017
- fulfills -> FEAT-021

## REQ-120: FR-S03-004 (Requirement)
The system shall display the plant's most recently logged photo as a full-width hero image. If no photos exist, a placeholder illustration for the plant's category shall be shown.
- Status: Planned
- fulfills -> FEAT-017
- fulfills -> FEAT-021

## REQ-121: FR-S03-005 (Requirement)
The hero image shall display a photo count badge (e.g., "12 photos"). Tapping the hero image shall navigate to SCR-15 Progress Reels Gallery filtered for this plant.
- Status: Planned
- fulfills -> FEAT-017
- fulfills -> FEAT-021

## REQ-122: FR-S03-006 (Requirement)
The hero area shall include an "Add Photo" button overlay that opens MOD-01 Quick Log Sheet pre-set to the photo capture step.
- Status: Planned
- fulfills -> FEAT-017
- fulfills -> FEAT-021

## REQ-123: FR-S03-007 (Requirement)
The system shall display a horizontal pill action row beneath the hero: Log, Diagnose, Share, and Archive. These shall remain visible when the user scrolls down (sticky below the hero or in the header).
- Status: Planned
- fulfills -> FEAT-017
- fulfills -> FEAT-021

## REQ-124: FR-S03-008 (Requirement)
Tapping "Log" shall open MOD-01 Quick Log Sheet pre-filled for this plant.
- Status: Planned
- fulfills -> FEAT-017
- fulfills -> FEAT-021

## REQ-125: FR-S03-009 (Requirement)
Tapping "Diagnose" shall navigate to SCR-06 Leaf Diagnostics.
- Status: Planned
- fulfills -> FEAT-017
- fulfills -> FEAT-021

## REQ-126: FR-S03-010 (Requirement)
Tapping "Share" shall open MOD-12 Export / Share Sheet for this plant.
- Status: Planned
- fulfills -> FEAT-017
- fulfills -> FEAT-021

## REQ-127: FR-S03-011 (Requirement)
Tapping "Archive" shall display a confirmation dialog. On confirmation, the plant shall be moved to SCR-14 Cemetery Log and removed from SCR-02 Plant List.
- Status: Planned
- fulfills -> FEAT-017
- fulfills -> FEAT-021

## REQ-128: FR-S03-012 (Requirement)
The system shall display a plant info card containing: species (common name + scientific name), growing method badge, current growing stage chip (Seedling / Veg / Bloom / Fruiting / Dormant), date added, location/zone tag, and container size (if the method is Container).
- Status: Planned
- fulfills -> FEAT-017
- fulfills -> FEAT-021

## REQ-129: FR-S03-013 (Requirement)
The growing stage shall be the most recently set value, editable by tapping the chip inline.
- Status: Planned
- fulfills -> FEAT-017
- fulfills -> FEAT-021

## REQ-130: FR-S03-014 (Requirement)
Tapping the Edit icon on the plant info card shall open MOD-02 Add / Edit Plant Sheet pre-filled with the current plant data.
- Status: Planned
- fulfills -> FEAT-017
- fulfills -> FEAT-021

## REQ-131: FR-S03-015 (Requirement)
The system shall display the individual Garden Health Score for this plant as a mini circular dial (0–100).
- Status: Planned
- fulfills -> FEAT-017
- fulfills -> FEAT-021

## REQ-132: FR-S03-016 (Requirement)
The system shall display an expandable 8-metric breakdown below the dial: Moisture, Light, pH, Growth Rate, Nutrient Level, Pest Risk, Temperature, and Humidity. Collapsed by default, expanding shows a bar chart or slider per metric with a plain-English label.
- Status: Planned
- fulfills -> FEAT-017
- fulfills -> FEAT-021

## REQ-133: FR-S03-017 (Requirement)
Tapping "View Full Insights →" shall expand the inline 8-metric chart without navigating away from the screen.
- Status: Planned
- fulfills -> FEAT-017
- fulfills -> FEAT-021

## REQ-134: FR-S03-018 (Requirement)
When a weather condition is forecast that affects this plant's care tasks within the next 3 days, the system shall display a dismissible smart alert banner (e.g., "Rain in 2 days → skip next watering"). The banner shall source data from the same cached weather API response used by SCR-01.
- Status: Planned
- fulfills -> FEAT-017
- fulfills -> FEAT-021

## REQ-135: FR-S03-019 (Requirement)
The system shall display the plant's care tasks due today as cards with "Done ✓" checkboxes. Checking a task shall mark it complete in the schedule and update the Garden Health Score accordingly.
- Status: Planned
- fulfills -> FEAT-017
- fulfills -> FEAT-021

## REQ-136: FR-S03-020 (Requirement)
Each task shall offer a "Reschedule" link. Tapping it shall open a date/time picker to move the task to a future date.
- Status: Planned
- fulfills -> FEAT-017
- fulfills -> FEAT-021

## REQ-137: FR-S03-021 (Requirement)
A "View full schedule →" link shall navigate to SCR-07 Smart Scheduler filtered for this plant.
- Status: Planned
- fulfills -> FEAT-017
- fulfills -> FEAT-021

## REQ-138: FR-S03-022 (Requirement)
When the system detects that the user has the same species (or close botanical relatives) growing under two different methods, it shall display a cross-method insight card comparing growth rates or outcomes (e.g., "Your hydro basil grew 20% faster than your soil basil → try adjusting nutrient strength for the soil batch").
- Status: Planned
- fulfills -> FEAT-017
- fulfills -> FEAT-021

## REQ-139: FR-S03-023 (Requirement)
The cross-method insight card shall be dismissible. Once dismissed, it shall not reappear unless new comparative data is available.
- Status: Planned
- fulfills -> FEAT-017
- fulfills -> FEAT-021

## REQ-140: FR-S03-024 (Requirement)
The system shall display a reverse-chronological timeline of all log entries for this plant. Each entry shall show: entry thumbnail (photo if logged), timestamp, activity type chip, and any metric values recorded.
- Status: Planned
- fulfills -> FEAT-017
- fulfills -> FEAT-021

## REQ-141: FR-S03-025 (Requirement)
Tapping a log entry shall expand it inline to show: the full-resolution photo, all recorded metrics, the written note, and a voice note playback button (if a voice note was recorded for that entry).
- Status: Planned
- fulfills -> FEAT-017
- fulfills -> FEAT-021

## REQ-142: FR-S03-026 (Requirement)
The timeline shall paginate, loading additional entries on "Load more" tap to avoid performance degradation with large log histories.
- Status: Planned
- fulfills -> FEAT-017
- fulfills -> FEAT-021

## REQ-143: FR-S03-027 (Requirement)
The system shall display at most one contextual tip card on Plant Detail, triggered by the content of the most recent log entry (e.g., if the last log recorded yellowing leaves, the tip card shall suggest the "Magnesium Deficiency Guide"). Tapping it shall open MOD-09.
- Status: Planned
- fulfills -> FEAT-017
- fulfills -> FEAT-021

## REQ-144: FR-S03-028 (Requirement)
The system shall display a persistent freeform notes text area with a microphone icon for voice input.
- Status: Planned
- fulfills -> FEAT-017
- fulfills -> FEAT-021

## REQ-145: FR-S03-029 (Requirement)
When the user taps the microphone icon and microphone permission has not been granted, the system shall trigger MOD-04 (Permission Context Modal — Mic) before opening voice recording.
- Status: Planned
- fulfills -> FEAT-017
- fulfills -> FEAT-021

## REQ-146: FR-S03-030 (Requirement)
Saved notes shall be timestamped and appended to the plant's log history.
- Status: Planned
- fulfills -> FEAT-017
- fulfills -> FEAT-021

## REQ-147: FR-S03-031 (Requirement)
The system shall display a "Log" FAB (bottom-right) always visible on Plant Detail. Tapping it shall open MOD-01 Quick Log Sheet pre-filled for this plant.
- Status: Planned
- fulfills -> FEAT-017
- fulfills -> FEAT-021

## REQ-148: FR-S15-001 (Requirement)
The system shall navigate to the Progress Reels Gallery when the user taps: the hero image on SCR-03, the "Progress Reels Gallery" link on SCR-11 Profile, or the "My Reels" row in SCR-11.
- Status: Planned
- fulfills -> FEAT-031
- fulfills -> FEAT-012

## REQ-149: FR-S15-002 (Requirement)
When navigated from SCR-03, the gallery shall open pre-filtered to show only reels for the originating plant.
- Status: Planned
- fulfills -> FEAT-031
- fulfills -> FEAT-012

## REQ-150: FR-S15-003 (Requirement)
A back arrow shall return the user to the previous screen.
- Status: Planned
- fulfills -> FEAT-031
- fulfills -> FEAT-012

## REQ-151: FR-S15-004 (Requirement)
The system shall display all generated reels in a 2-column grid. Each card shall show: video thumbnail with a play icon overlay, the plant name, the date range covered by the reel, and the reel duration.
- Status: Planned
- fulfills -> FEAT-031
- fulfills -> FEAT-012

## REQ-152: FR-S15-005 (Requirement)
The system shall display filter chips above the grid: All, By Plant, By Method, By Date.
- Status: Planned
- fulfills -> FEAT-031
- fulfills -> FEAT-012

## REQ-153: FR-S15-006 (Requirement)
When the user has no reels, the system shall display an empty state with the heading "No reels yet," the sub-label "Your first reel needs at least 3 logged photos," and a "Go to My Garden →" button linking to SCR-02.
- Status: Planned
- fulfills -> FEAT-031
- fulfills -> FEAT-012

## REQ-154: FR-S15-007 (Requirement)
Tapping a reel card shall open a full-screen playback view with the reel auto-playing muted.
- Status: Planned
- fulfills -> FEAT-031
- fulfills -> FEAT-012

## REQ-155: FR-S15-008 (Requirement)
The playback view shall display a method-specific data overlay on the video: method badge and key metrics recorded during the reel's date range.
- Status: Planned
- fulfills -> FEAT-031
- fulfills -> FEAT-012

## REQ-156: FR-S15-009 (Requirement)
The system shall display the GardenPulse watermark on all reel playback and exports by default. Users who have purchased the Supporter Badge (MOD-07) shall have the option to toggle the watermark off.
- Status: Planned
- fulfills -> FEAT-031
- fulfills -> FEAT-012

## REQ-157: FR-S15-010 (Requirement)
The playback view shall provide: a Share button (opens MOD-12), a Download button (triggers MOD-05 Rewarded Video Prompt before downloading), an Edit button (allows trimming the date range and toggling the overlay), and a Close (×) button.
- Status: Planned
- fulfills -> FEAT-031
- fulfills -> FEAT-012

## REQ-158: FR-S15-011 (Requirement)
Tapping "+ Create" shall start a 4-step reel generation flow: (1) plant selector from the user's plant list, (2) date range picker with start and end date, (3) a preview strip showing the sequence of logged photos for that range, (4) a style selector for overlay options.
- Status: Planned
- fulfills -> FEAT-031
- fulfills -> FEAT-012

## REQ-159: FR-S15-012 (Requirement)
The system shall require a minimum of 3 logged photos for a plant before allowing reel generation for that plant.
- Status: Planned
- fulfills -> FEAT-031
- fulfills -> FEAT-012

## REQ-160: FR-S15-013 (Requirement)
Tapping "Generate Reel" in step 4 shall trigger a loading animation and then produce the reel locally on-device. The completed reel shall be added to the gallery grid.
- Status: Planned
- fulfills -> FEAT-031
- fulfills -> FEAT-012

## REQ-161: FR-S04-001 (Requirement)
The system shall display the Tools Hub when the user taps the Tools tab in the bottom navigation bar.
- Status: Planned
- fulfills -> FEAT-015
- fulfills -> FEAT-011
- fulfills -> FEAT-008
- fulfills -> FEAT-013

## REQ-162: FR-S04-002 (Requirement)
The system shall display four tool cards: Nutrient / Recipe Calculator, Leaf Diagnostics, Smart Scheduler, and QR / Label Scanner. Each card shall show a distinct icon, title, and one-line description.
- Status: Planned
- fulfills -> FEAT-015
- fulfills -> FEAT-011
- fulfills -> FEAT-008
- fulfills -> FEAT-013

## REQ-163: FR-S04-003 (Requirement)
After the user has opened any tool at least once, the system shall display a "Recently Used" section at the top of the Tools Hub containing the last-used tool card with an "Open again →" link.
- Status: Planned
- fulfills -> FEAT-015
- fulfills -> FEAT-011
- fulfills -> FEAT-008
- fulfills -> FEAT-013

## REQ-164: FR-S04-004 (Requirement)
Tapping the Nutrient / Recipe Calculator card shall navigate to SCR-05.
- Status: Planned
- fulfills -> FEAT-015
- fulfills -> FEAT-011
- fulfills -> FEAT-008
- fulfills -> FEAT-013

## REQ-165: FR-S04-005 (Requirement)
Tapping the Leaf Diagnostics card shall navigate to SCR-06.
- Status: Planned
- fulfills -> FEAT-015
- fulfills -> FEAT-011
- fulfills -> FEAT-008
- fulfills -> FEAT-013

## REQ-166: FR-S04-006 (Requirement)
Tapping the Smart Scheduler card shall navigate to SCR-07.
- Status: Planned
- fulfills -> FEAT-015
- fulfills -> FEAT-011
- fulfills -> FEAT-008
- fulfills -> FEAT-013

## REQ-167: FR-S04-007 (Requirement)
Tapping the QR / Label Scanner card shall trigger MOD-03 QR Scanner Overlay.
- Status: Planned
- fulfills -> FEAT-015
- fulfills -> FEAT-011
- fulfills -> FEAT-008
- fulfills -> FEAT-013

## REQ-168: FR-S04-008 (Requirement)
The system shall provide a search field in the header. As the user types, the tool cards shall filter to show only matching tools by name or description keyword.
- Status: Planned
- fulfills -> FEAT-015
- fulfills -> FEAT-011
- fulfills -> FEAT-008
- fulfills -> FEAT-013

## REQ-169: FR-S04-009 (Requirement)
The system shall display one native ad slot in the Tools Hub, positioned between the first and second row of tool cards.
- Status: Planned
- fulfills -> FEAT-015
- fulfills -> FEAT-011
- fulfills -> FEAT-008
- fulfills -> FEAT-013

## REQ-170: FR-S05-001 (Requirement)
The system shall navigate to the Nutrient / Recipe Calculator from SCR-04 Tools Hub.
- Status: Planned
- fulfills -> FEAT-015

## REQ-171: FR-S05-002 (Requirement)
A back arrow in the header shall return the user to SCR-04.
- Status: Planned
- fulfills -> FEAT-015

## REQ-172: FR-S05-003 (Requirement)
An "ℹ" info icon shall display a dismissible tooltip: "All calculations are method-specific estimates. Always verify with manufacturer guidelines."
- Status: Planned
- fulfills -> FEAT-015

## REQ-173: FR-S05-004 (Requirement)
The system shall provide a required method selector with three options: Soil Drench, Hydro Reservoir, and Foliar Spray. The method shall be pre-selected based on the user's primary growing profile but shall be editable per calculation.
- Status: Planned
- fulfills -> FEAT-015

## REQ-174: FR-S05-005 (Requirement)
The system shall provide a nutrient brand selector field with autocomplete from a locally stored brand database. The field shall also accept free-text entry for brands not in the database.
- Status: Planned
- fulfills -> FEAT-015

## REQ-175: FR-S05-006 (Requirement)
The system shall provide a "Scan label" button next to the brand selector that opens MOD-03 QR Scanner Overlay. If the scanned product is found in the brand database, the brand selector shall be auto-filled.
- Status: Planned
- fulfills -> FEAT-015

## REQ-176: FR-S05-007 (Requirement)
The system shall provide a water volume input field with a numeric keyboard and a unit toggle (Litres / Gallons). The unit shall default to the user's locale-detected unit system.
- Status: Planned
- fulfills -> FEAT-015

## REQ-177: FR-S05-008 (Requirement)
The system shall provide a required growth stage selector with four options: Seedling, Veg / Grow, Bloom / Flower, Flush / Ripening.
- Status: Planned
- fulfills -> FEAT-015

## REQ-178: FR-S05-009 (Requirement)
The system shall provide an optional Target EC / PPM field. When a known brand is selected, the system shall pre-fill this field with the brand's recommended default for the selected method and growth stage.
- Status: Planned
- fulfills -> FEAT-015

## REQ-179: FR-S05-010 (Requirement)
The system shall display a pH target range derived from the selected method and growth stage. The displayed range shall be editable by the user.
- Status: Planned
- fulfills -> FEAT-015

## REQ-180: FR-S05-011 (Requirement)
The "Generate Recipe" button shall be disabled until the following required fields are filled: Method, Nutrient Brand (or any free-text entry), Water Volume, and Growth Stage.
- Status: Planned
- fulfills -> FEAT-015

## REQ-181: FR-S05-012 (Requirement)
When the user taps "Generate Recipe," the system shall trigger MOD-06 Interstitial Ad displayed over a 1.5-second animated loading state. After the ad completes or is dismissed, the results card shall appear.
- Status: Planned
- fulfills -> FEAT-015

## REQ-182: FR-S05-013 (Requirement)
The results card shall display per-nutrient rows, each containing: nutrient name, calculated dose amount, unit, and a colour-coded indicator (green = within safe range, amber = near limit, red = exceeds guideline).
- Status: Planned
- fulfills -> FEAT-015

## REQ-183: FR-S05-014 (Requirement)
The results card shall display the pH target range as a visual band with the calculated working value indicated.
- Status: Planned
- fulfills -> FEAT-015

## REQ-184: FR-S05-015 (Requirement)
The results card shall display the EC / PPM target value.
- Status: Planned
- fulfills -> FEAT-015

## REQ-185: FR-S05-016 (Requirement)
The results card shall display any applicable warnings or notes (e.g., "Reduce by 25% for seedlings under 2 weeks old").
- Status: Planned
- fulfills -> FEAT-015

## REQ-186: FR-S05-017 (Requirement)
The system shall provide a "Save Recipe" button that logs the recipe to the selected plant's history or creates a standalone saved recipe if no plant is selected.
- Status: Planned
- fulfills -> FEAT-015

## REQ-187: FR-S05-018 (Requirement)
The system shall provide an "Add to Schedule" link that pre-fills SCR-07 Smart Scheduler with a feeding task using the current recipe's data.
- Status: Planned
- fulfills -> FEAT-015

## REQ-188: FR-S05-019 (Requirement)
The system shall provide an "Export / Share" button in the results card. Tapping it shall trigger MOD-05 Rewarded Video Prompt. After successful video completion, MOD-12 Export / Share Sheet shall open.
- Status: Planned
- fulfills -> FEAT-015

## REQ-189: FR-S05-020 (Requirement)
The PDF export format shall include: the full nutrient dose table, pH and EC/PPM targets, method, growth stage, water volume, and the GardenPulse branding.
- Status: Planned
- fulfills -> FEAT-015

## REQ-190: FR-S05-021 (Requirement)
A persistent unit toggle (Metric / Imperial) shall be visible below the results card. Switching units shall instantly recalculate and redisplay all dose amounts and volumes.
- Status: Planned
- fulfills -> FEAT-015

## REQ-191: FR-S06-001 (Requirement)
The system shall navigate to Leaf Diagnostics from SCR-04 Tools Hub and from the "Diagnose" action pill on SCR-03 Plant Detail.
- Status: Planned
- fulfills -> FEAT-011
- fulfills -> FEAT-001
- fulfills -> FEAT-002

## REQ-192: FR-S06-002 (Requirement)
A back arrow shall return the user to the originating screen.
- Status: Planned
- fulfills -> FEAT-011
- fulfills -> FEAT-001
- fulfills -> FEAT-002

## REQ-193: FR-S06-003 (Requirement)
Upon entering Leaf Diagnostics, if camera permission has not been granted, the system shall immediately trigger MOD-04 (Permission Context Modal — Camera) before showing any camera UI.
- Status: Planned
- fulfills -> FEAT-011
- fulfills -> FEAT-001
- fulfills -> FEAT-002

## REQ-194: FR-S06-004 (Requirement)
If the user denies camera permission, the system shall display a "Permission denied" state with: an illustration, a "Camera access is needed for diagnostics" label, an "Open Settings" button (deep-links to device settings), and a "Use Gallery Instead" fallback button.
- Status: Planned
- fulfills -> FEAT-011
- fulfills -> FEAT-001
- fulfills -> FEAT-002

## REQ-195: FR-S06-005 (Requirement)
The system shall display a live camera viewfinder with a leaf-shaped alignment frame overlay and the instruction label "Centre the leaf in frame."
- Status: Planned
- fulfills -> FEAT-011
- fulfills -> FEAT-001
- fulfills -> FEAT-002

## REQ-196: FR-S06-006 (Requirement)
The system shall provide a Capture button (large circle) for taking the diagnostic photo.
- Status: Planned
- fulfills -> FEAT-011
- fulfills -> FEAT-001
- fulfills -> FEAT-002

## REQ-197: FR-S06-007 (Requirement)
The system shall provide a gallery import button allowing the user to import an existing photo from their device photo library instead of capturing a new one.
- Status: Planned
- fulfills -> FEAT-011
- fulfills -> FEAT-001
- fulfills -> FEAT-002

## REQ-198: FR-S06-008 (Requirement)
The system shall provide a flash/torch toggle icon on the viewfinder.
- Status: Planned
- fulfills -> FEAT-011
- fulfills -> FEAT-001
- fulfills -> FEAT-002

## REQ-199: FR-S06-009 (Requirement)
Upon capture or import, the system shall display a full-screen loading state with the label "Analysing on-device…" and an animated scan-line animation, plus a privacy badge reading "Your photo never leaves your device."
- Status: Planned
- fulfills -> FEAT-011
- fulfills -> FEAT-001
- fulfills -> FEAT-002

## REQ-200: FR-S06-010 (Requirement)
All image analysis SHALL run on-device using local machine learning inference. The captured image shall NEVER be uploaded to any external server or API.
- Status: Planned
- fulfills -> FEAT-011
- fulfills -> FEAT-001
- fulfills -> FEAT-002

## REQ-201: FR-S06-011 (Requirement)
The system shall strip all photo metadata (EXIF location, device info) from the image before analysis. Metadata shall not be stored unless the user has opted into photo storage in SCR-13 Privacy Dashboard.
- Status: Planned
- fulfills -> FEAT-011
- fulfills -> FEAT-001
- fulfills -> FEAT-002

## REQ-202: FR-S06-012 (Requirement)
The results card shall display: the identified plant name (common + scientific name) with a confidence percentage badge, and the detected growing method.
- Status: Planned
- fulfills -> FEAT-011
- fulfills -> FEAT-001
- fulfills -> FEAT-002

## REQ-203: FR-S06-013 (Requirement)
The results card shall display the primary issue identified (e.g., "Magnesium Deficiency") with a confidence percentage and a severity badge (Low / Medium / High, colour-coded: green / amber / red).
- Status: Planned
- fulfills -> FEAT-011
- fulfills -> FEAT-001
- fulfills -> FEAT-002

## REQ-204: FR-S06-014 (Requirement)
The results card shall display a brief explanation (2 lines) of the primary issue and a numbered list of suggested corrective actions.
- Status: Planned
- fulfills -> FEAT-011
- fulfills -> FEAT-001
- fulfills -> FEAT-002

## REQ-205: FR-S06-015 (Requirement)
The system shall support listing secondary issues in a collapsed expandable section below the primary finding.
- Status: Planned
- fulfills -> FEAT-011
- fulfills -> FEAT-001
- fulfills -> FEAT-002

## REQ-206: FR-S06-016 (Requirement)
The results card shall include a contextual tip link (e.g., "Read: Magnesium Deficiency Guide") that opens MOD-09 with the relevant article.
- Status: Planned
- fulfills -> FEAT-011
- fulfills -> FEAT-001
- fulfills -> FEAT-002

## REQ-207: FR-S06-017 (Requirement)
The system shall provide a "Log This Diagnosis" button that creates a log entry for the linked plant (or prompts plant selection if opened from SCR-04 directly) with the diagnosis result appended to the log.
- Status: Planned
- fulfills -> FEAT-011
- fulfills -> FEAT-001
- fulfills -> FEAT-002

## REQ-208: FR-S06-018 (Requirement)
The system shall provide a "Try Again / Retake" button that returns the user to the camera viewfinder.
- Status: Planned
- fulfills -> FEAT-011
- fulfills -> FEAT-001
- fulfills -> FEAT-002

## REQ-209: FR-S06-019 (Requirement)
The system shall provide a "Share Results" button that opens MOD-12 Export / Share Sheet with a summary of the diagnosis as the shareable content.
- Status: Planned
- fulfills -> FEAT-011
- fulfills -> FEAT-001
- fulfills -> FEAT-002

## REQ-210: FR-S06-020 (Requirement)
The system shall maintain a local history of all past diagnoses. The history section shall display entries as a list with: date, thumbnail, identified plant name, primary finding, and severity badge.
- Status: Planned
- fulfills -> FEAT-011
- fulfills -> FEAT-001
- fulfills -> FEAT-002

## REQ-211: FR-S06-021 (Requirement)
The history section shall be filterable by: All, Deficiency, Pest, Disease, Overwatering.
- Status: Planned
- fulfills -> FEAT-011
- fulfills -> FEAT-001
- fulfills -> FEAT-002

## REQ-212: FR-S07-001 (Requirement)
The system shall navigate to Smart Scheduler from SCR-04 Tools Hub, from the "See full schedule →" link on SCR-01 Dashboard, and from the "View full schedule →" link on SCR-03 Plant Detail.
- Status: Planned
- fulfills -> FEAT-008
- fulfills -> FEAT-009
- fulfills -> FEAT-010

## REQ-213: FR-S07-002 (Requirement)
When navigated from SCR-03 Plant Detail, the scheduler shall open with the view filtered to show only tasks for that plant.
- Status: Planned
- fulfills -> FEAT-008
- fulfills -> FEAT-009
- fulfills -> FEAT-010

## REQ-214: FR-S07-003 (Requirement)
A back arrow shall return the user to the originating screen.
- Status: Planned
- fulfills -> FEAT-008
- fulfills -> FEAT-009
- fulfills -> FEAT-010

## REQ-215: FR-S07-004 (Requirement)
The system shall display a week-strip calendar view by default. A toggle in the header shall switch between week and monthly grid views.
- Status: Planned
- fulfills -> FEAT-008
- fulfills -> FEAT-009
- fulfills -> FEAT-010

## REQ-216: FR-S07-005 (Requirement)
In the week-strip view, each day cell shall show coloured dots for scheduled tasks, colour-coded by task type: blue (Water), green (Feed), yellow (Prune), red (urgent/overdue).
- Status: Planned
- fulfills -> FEAT-008
- fulfills -> FEAT-009
- fulfills -> FEAT-010

## REQ-217: FR-S07-006 (Requirement)
The current day shall be visually highlighted with a ring or background accent.
- Status: Planned
- fulfills -> FEAT-008
- fulfills -> FEAT-009
- fulfills -> FEAT-010

## REQ-218: FR-S07-007 (Requirement)
The system shall display sunrise and sunset times for the selected day, derived from the user's detected zone and date.
- Status: Planned
- fulfills -> FEAT-008
- fulfills -> FEAT-009
- fulfills -> FEAT-010

## REQ-219: FR-S07-008 (Requirement)
Tapping any day cell shall display the task list for that day in the section below the calendar.
- Status: Planned
- fulfills -> FEAT-008
- fulfills -> FEAT-009
- fulfills -> FEAT-010

## REQ-220: FR-S07-009 (Requirement)
The system shall display the task list for the selected day. Each task row shall show: the plant thumbnail, plant name, task type chip, and a "Done ✓" checkbox.
- Status: Planned
- fulfills -> FEAT-008
- fulfills -> FEAT-009
- fulfills -> FEAT-010

## REQ-221: FR-S07-010 (Requirement)
Marking a task as done shall update the plant's log and remove the task from the overdue list.
- Status: Planned
- fulfills -> FEAT-008
- fulfills -> FEAT-009
- fulfills -> FEAT-010

## REQ-222: FR-S07-011 (Requirement)
The system shall support a swipe-left action on each task row with two options: Reschedule (opens a date picker) and Skip (removes the task from this day only, without rescheduling).
- Status: Planned
- fulfills -> FEAT-008
- fulfills -> FEAT-009
- fulfills -> FEAT-010

## REQ-223: FR-S07-012 (Requirement)
The system shall provide a "Mark All Done" button at the top of the task list for the selected day, which marks all tasks for that day as complete.
- Status: Planned
- fulfills -> FEAT-008
- fulfills -> FEAT-009
- fulfills -> FEAT-010

## REQ-224: FR-S07-013 (Requirement)
The system shall provide a "Weather sync" toggle. When enabled, the system shall automatically remove or suppress watering tasks on days where rain probability is ≥70%, and restore them if the forecast changes before the day begins.
- Status: Planned
- fulfills -> FEAT-008
- fulfills -> FEAT-009
- fulfills -> FEAT-010

## REQ-225: FR-S07-014 (Requirement)
The system shall provide a "Skip weekends" toggle. When enabled, no new tasks shall be scheduled on Saturdays and Sundays, and existing weekend tasks shall be rescheduled to the nearest weekday.
- Status: Planned
- fulfills -> FEAT-008
- fulfills -> FEAT-009
- fulfills -> FEAT-010

## REQ-226: FR-S07-015 (Requirement)
The system shall provide a "Travel Mode" toggle with a date range picker. When Travel Mode is active for the selected date range, all notifications and task reminders shall be suppressed. The schedule data shall remain intact.
- Status: Planned
- fulfills -> FEAT-008
- fulfills -> FEAT-009
- fulfills -> FEAT-010

## REQ-227: FR-S07-016 (Requirement)
The system shall provide a reminder time preference selector: Morning (7–9 AM), Afternoon (12–2 PM), Evening (6–8 PM). The selected preference shall apply to all scheduled task notifications.
- Status: Planned
- fulfills -> FEAT-008
- fulfills -> FEAT-009
- fulfills -> FEAT-010

## REQ-228: FR-S07-017 (Requirement)
The system shall automatically adjust scheduled reminder times when a timezone change or DST transition is detected on the device.
- Status: Planned
- fulfills -> FEAT-008
- fulfills -> FEAT-009
- fulfills -> FEAT-010

## REQ-229: FR-S07-018 (Requirement)
The system shall provide an "+ Add Custom Reminder" button that opens an inline form with: plant selector, task type selector, repeat frequency (Once / Daily / Weekly / Custom), and a date + time picker.
- Status: Planned
- fulfills -> FEAT-008
- fulfills -> FEAT-009
- fulfills -> FEAT-010

## REQ-230: FR-S07-019 (Requirement)
Custom reminders shall appear alongside auto-generated care tasks in the calendar and task list views.
- Status: Planned
- fulfills -> FEAT-008
- fulfills -> FEAT-009
- fulfills -> FEAT-010

## REQ-231: FR-S07-020 (Requirement)
A "Notification preferences →" quick link shall open MOD-10 Notification Preferences Sheet.
- Status: Planned
- fulfills -> FEAT-008
- fulfills -> FEAT-009
- fulfills -> FEAT-010

## REQ-232: FR-S08-001 (Requirement)
The system shall display the Community Hub when the user taps the Community tab in the bottom navigation bar.
- Status: Planned
- fulfills -> FEAT-028
- fulfills -> FEAT-029
- fulfills -> FEAT-030
- fulfills -> FEAT-007
- fulfills -> FEAT-026

## REQ-233: FR-S08-002 (Requirement)
The system shall display a local context banner at the top of the Community Hub showing the heading "What's thriving in [City] right now 🌱" and one anonymized aggregate insight (e.g., "Cherry tomatoes: 87% success in Berlin balconies"). The city name shall match the user's detected or manually entered location.
- Status: Planned
- fulfills -> FEAT-028
- fulfills -> FEAT-029
- fulfills -> FEAT-030
- fulfills -> FEAT-007
- fulfills -> FEAT-026

## REQ-234: FR-S08-003 (Requirement)
The banner shall include a "View Map →" link that navigates to SCR-10 Local Grow Map.
- Status: Planned
- fulfills -> FEAT-028
- fulfills -> FEAT-029
- fulfills -> FEAT-030
- fulfills -> FEAT-007
- fulfills -> FEAT-026

## REQ-235: FR-S08-004 (Requirement)
The Community Hub shall contain an internal tab bar with three tabs: Local, Clusters, and Challenges.
- Status: Planned
- fulfills -> FEAT-028
- fulfills -> FEAT-029
- fulfills -> FEAT-030
- fulfills -> FEAT-007
- fulfills -> FEAT-026

## REQ-236: FR-S08-005 (Requirement)
The Local tab shall display anonymized success stats cards for the user's zone. Each card shall show: plant name, success percentage, number of growers, and a trending direction arrow.
- Status: Planned
- fulfills -> FEAT-028
- fulfills -> FEAT-029
- fulfills -> FEAT-030
- fulfills -> FEAT-007
- fulfills -> FEAT-026

## REQ-237: FR-S08-006 (Requirement)
The Local tab stats shall display only aggregate, anonymized data. No individual user data or precise locations shall be shown.
- Status: Planned
- fulfills -> FEAT-028
- fulfills -> FEAT-029
- fulfills -> FEAT-030
- fulfills -> FEAT-007
- fulfills -> FEAT-026

## REQ-238: FR-S08-007 (Requirement)
A "View Full Map →" button shall navigate to SCR-10.
- Status: Planned
- fulfills -> FEAT-028
- fulfills -> FEAT-029
- fulfills -> FEAT-030
- fulfills -> FEAT-007
- fulfills -> FEAT-026

## REQ-239: FR-S08-008 (Requirement)
The Clusters tab shall display a "My Clusters" section (clusters the user has joined) and a "Nearby Clusters" section (suggested clusters based on the user's location and growing method).
- Status: Planned
- fulfills -> FEAT-028
- fulfills -> FEAT-029
- fulfills -> FEAT-030
- fulfills -> FEAT-007
- fulfills -> FEAT-026

## REQ-240: FR-S08-009 (Requirement)
Each cluster card shall display: cluster name, member count, method/interest tag, recent activity indicator, and a Join / Joined toggle button.
- Status: Planned
- fulfills -> FEAT-028
- fulfills -> FEAT-029
- fulfills -> FEAT-030
- fulfills -> FEAT-007
- fulfills -> FEAT-026

## REQ-241: FR-S08-010 (Requirement)
Tapping a cluster card in "My Clusters" shall navigate to SCR-09 Garden Cluster Detail.
- Status: Planned
- fulfills -> FEAT-028
- fulfills -> FEAT-029
- fulfills -> FEAT-030
- fulfills -> FEAT-007
- fulfills -> FEAT-026

## REQ-242: FR-S08-011 (Requirement)
A "+ Join a Cluster" CTA button shall open a searchable cluster browse sheet allowing the user to search by name, location, or method interest.
- Status: Planned
- fulfills -> FEAT-028
- fulfills -> FEAT-029
- fulfills -> FEAT-030
- fulfills -> FEAT-007
- fulfills -> FEAT-026

## REQ-243: FR-S08-012 (Requirement)
Tapping "Join" on a nearby cluster card shall add the cluster to "My Clusters" and confirm with a brief success toast.
- Status: Planned
- fulfills -> FEAT-028
- fulfills -> FEAT-029
- fulfills -> FEAT-030
- fulfills -> FEAT-007
- fulfills -> FEAT-026

## REQ-244: FR-S08-013 (Requirement)
The Challenges tab shall display the currently active weekly challenge as a card, showing: challenge title, end date countdown, total entry count, and a "Submit Entry" button.
- Status: Planned
- fulfills -> FEAT-028
- fulfills -> FEAT-029
- fulfills -> FEAT-030
- fulfills -> FEAT-007
- fulfills -> FEAT-026

## REQ-245: FR-S08-014 (Requirement)
Tapping "Submit Entry" for a challenge shall open MOD-01 Quick Log Sheet pre-configured to capture a photo and caption for the challenge submission.
- Status: Planned
- fulfills -> FEAT-028
- fulfills -> FEAT-029
- fulfills -> FEAT-030
- fulfills -> FEAT-007
- fulfills -> FEAT-026

## REQ-246: FR-S08-015 (Requirement)
The Challenges tab shall display a past challenges section with winner spotlight cards. Each spotlight shall show an anonymized photo, method badge, and the challenge name. No personally identifiable information shall be displayed.
- Status: Planned
- fulfills -> FEAT-028
- fulfills -> FEAT-029
- fulfills -> FEAT-030
- fulfills -> FEAT-007
- fulfills -> FEAT-026

## REQ-247: FR-S08-016 (Requirement)
The system shall display a referral banner on the Community Hub: "Invite 3 friends → unlock Multi-Zone Management" with a progress indicator showing how many friends have been referred out of the required 3, and a "Share Invite Link" button that opens MOD-12.
- Status: Planned
- fulfills -> FEAT-028
- fulfills -> FEAT-029
- fulfills -> FEAT-030
- fulfills -> FEAT-007
- fulfills -> FEAT-026

## REQ-248: FR-S08-017 (Requirement)
The system shall display one geo-targeted native ad slot on the Community Hub, positioned below the Local tab content and styled to match the surrounding community cards.
- Status: Planned
- fulfills -> FEAT-028
- fulfills -> FEAT-029
- fulfills -> FEAT-030
- fulfills -> FEAT-007
- fulfills -> FEAT-026

## REQ-249: FR-S09-001 (Requirement)
The system shall navigate to Garden Cluster Detail when the user taps a joined cluster card from SCR-08 Community Hub.
- Status: Planned
- fulfills -> FEAT-029

## REQ-250: FR-S09-002 (Requirement)
A back arrow shall return the user to SCR-08 Community Hub.
- Status: Planned
- fulfills -> FEAT-029

## REQ-251: FR-S09-003 (Requirement)
The system shall display the cluster's cover image (or a default gradient), cluster name, member count, location or interest tag, description text (expandable beyond 3 lines), and the cluster creation date.
- Status: Planned
- fulfills -> FEAT-029

## REQ-252: FR-S09-004 (Requirement)
The system shall display a Join / Leave toggle button. Tapping "Join" shall add the cluster to the user's joined clusters list and confirm with a success toast. Tapping "Leave" shall display a confirmation dialog before removing the cluster.
- Status: Planned
- fulfills -> FEAT-029

## REQ-253: FR-S09-005 (Requirement)
The Cluster Detail shall contain an internal tab bar: Posts, Members, Swaps, and Challenges.
- Status: Planned
- fulfills -> FEAT-029

## REQ-254: FR-S09-006 (Requirement)
The Posts tab shall display a reverse-chronological feed of posts from cluster members. Each post shall show: anonymized avatar, anonymized username handle, post text with optional method tag chip, and optionally a plant photo.
- Status: Planned
- fulfills -> FEAT-029

## REQ-255: FR-S09-007 (Requirement)
Each post shall provide: a Like count with Like button, a Comment count with Comment button, a bookmark icon ("Save Plant" to add the discussed plant to the user's watchlist), and a Report (⚑) icon for content moderation.
- Status: Planned
- fulfills -> FEAT-029

## REQ-256: FR-S09-008 (Requirement)
Tapping a photo on a post shall open a full-screen image viewer with a "Log this plant →" CTA that opens MOD-02 Add / Edit Plant Sheet pre-filled with the plant shown.
- Status: Planned
- fulfills -> FEAT-029

## REQ-257: FR-S09-009 (Requirement)
Tapping the Comment button shall expand an inline comment thread below the post.
- Status: Planned
- fulfills -> FEAT-029

## REQ-258: FR-S09-010 (Requirement)
The system shall provide a "Post to Cluster" FAB (bottom-right). Tapping it shall open an inline compose overlay with: a text field, a camera icon (triggers MOD-04 if camera permission not granted), a "@ Tag plants" button to link the post to a plant in the user's garden, and a method selector chip.
- Status: Planned
- fulfills -> FEAT-029

## REQ-259: FR-S09-011 (Requirement)
The Members tab shall display a list of cluster members with: anonymized avatar, anonymized username handle, method badges, and the date they joined the cluster. No real names, email addresses, or locations shall be displayed.
- Status: Planned
- fulfills -> FEAT-029

## REQ-260: FR-S09-012 (Requirement)
The system shall display a summary label: "X members growing Y together" at the top of the Members tab.
- Status: Planned
- fulfills -> FEAT-029

## REQ-261: FR-S09-015 (Requirement)
The Challenges tab shall display any active cluster-specific challenge with a "Submit Entry" button that opens MOD-01 Quick Log Sheet.
- Status: Planned
- fulfills -> FEAT-029

## REQ-262: FR-S09-016 (Requirement)
The system shall provide a challenge entry share button that opens MOD-12 Export / Share Sheet.
- Status: Planned
- fulfills -> FEAT-029

## REQ-263: FR-S10-001 (Requirement)
The system shall navigate to the Local Grow Map from the "View Map →" link on SCR-08 Community Hub and from the Local tab banner.
- Status: Planned
- fulfills -> FEAT-028
- fulfills -> FEAT-007

## REQ-264: FR-S10-002 (Requirement)
A back arrow shall return the user to SCR-08.
- Status: Planned
- fulfills -> FEAT-028
- fulfills -> FEAT-007

## REQ-265: FR-S10-003 (Requirement)
The system shall display an interactive map as the primary view, occupying approximately 60% of the screen height.
- Status: Planned
- fulfills -> FEAT-028
- fulfills -> FEAT-007

## REQ-266: FR-S10-004 (Requirement)
The map shall display anonymized success clusters as coloured dot markers, grouped by crop or plant category. Dot colour shall indicate crop category.
- Status: Planned
- fulfills -> FEAT-028
- fulfills -> FEAT-007

## REQ-267: FR-S10-005 (Requirement)
The map shall display the user's location as a soft-glow pin at zone or city level. The map SHALL NOT display the user's precise GPS coordinates or street-level position.
- Status: Planned
- fulfills -> FEAT-028
- fulfills -> FEAT-007

## REQ-268: FR-S10-006 (Requirement)
The map shall support standard pan and pinch-to-zoom gestures.
- Status: Planned
- fulfills -> FEAT-028
- fulfills -> FEAT-007

## REQ-269: FR-S10-007 (Requirement)
A layer toggle icon shall open a layer options sheet with three selectable views: Success Rate heat layer, Active Growers count layer, and Recent Logs (last 7 days) layer.
- Status: Planned
- fulfills -> FEAT-028
- fulfills -> FEAT-007

## REQ-270: FR-S10-008 (Requirement)
Crop filter chips (All, Tomatoes, Herbs, Leafy Greens, Root Veg, Fruit, Hydro) shall filter the visible clusters on the map in real time when tapped.
- Status: Planned
- fulfills -> FEAT-028
- fulfills -> FEAT-007

## REQ-271: FR-S10-009 (Requirement)
Tapping any cluster dot on the map shall open a bottom-sheet popup card displaying: the crop name, the number of growers in that area, the success rate percentage, the top local tip (sourced from the highest-upvoted community post for that crop and zone), and the relevant method tags.
- Status: Planned
- fulfills -> FEAT-028
- fulfills -> FEAT-007

## REQ-272: FR-S10-010 (Requirement)
The popup card shall provide a "Grow This Plant →" CTA button that opens MOD-02 Add / Edit Plant Sheet pre-filled with the crop's species data.
- Status: Planned
- fulfills -> FEAT-028
- fulfills -> FEAT-007

## REQ-273: FR-S10-011 (Requirement)
The popup card shall provide a "View Cluster →" link that navigates to the relevant SCR-09 Garden Cluster Detail if a matching cluster exists.
- Status: Planned
- fulfills -> FEAT-028
- fulfills -> FEAT-007

## REQ-274: FR-S10-012 (Requirement)
Below the map, the system shall display a statistics strip showing: total plants tracked in the user's city, the most popular plant this season in the user's zone, and the user's zone label.
- Status: Planned
- fulfills -> FEAT-028
- fulfills -> FEAT-007

## REQ-275: FR-S10-013 (Requirement)
The map shall display a persistent privacy footer with the label "All data anonymized — location only shared at zone level" and a "Privacy settings →" link to SCR-13.
- Status: Planned
- fulfills -> FEAT-028
- fulfills -> FEAT-007

## REQ-276: FR-S10-014 (Requirement)
All data shown on the Local Grow Map shall be aggregated and anonymized. No individual user data, usernames, or precise locations shall be displayed on or derivable from the map.
- Status: Planned
- fulfills -> FEAT-028
- fulfills -> FEAT-007

## REQ-277: FR-S11-001 (Requirement)
The system shall display the Profile & Badges screen when the user taps the Profile tab in the bottom navigation bar.
- Status: Planned
- fulfills -> FEAT-030
- fulfills -> FEAT-022

## REQ-278: FR-S11-002 (Requirement)
Tapping the settings icon in the header shall navigate to SCR-12 Settings.
- Status: Planned
- fulfills -> FEAT-030
- fulfills -> FEAT-022

## REQ-279: FR-S11-003 (Requirement)
The system shall display the user's avatar (default illustrated avatar or camera-uploaded image), display name or placeholder ("GardenPulse Grower"), and a growing profile tag auto-generated from their methods and location (e.g., "Hydro + Balcony · Berlin").
- Status: Planned
- fulfills -> FEAT-030
- fulfills -> FEAT-022

## REQ-280: FR-S11-004 (Requirement)
Tapping "Edit Profile" shall allow the user to update their display name and upload or change their avatar photo.
- Status: Planned
- fulfills -> FEAT-030
- fulfills -> FEAT-022

## REQ-281: FR-S11-005 (Requirement)
The system shall display the user's overall Garden Health Score as a large circular dial (0–100) with a week-over-week delta label (e.g., "+5 this week" or "−2 this week").
- Status: Planned
- fulfills -> FEAT-030
- fulfills -> FEAT-022

## REQ-282: FR-S11-006 (Requirement)
Tapping "View Breakdown →" shall expand an accordion beneath the dial showing all 8 Health Score metrics with individual values and short plain-English explanations.
- Status: Planned
- fulfills -> FEAT-030
- fulfills -> FEAT-022

## REQ-283: FR-S11-007 (Requirement)
The system shall display a horizontal stats row with four pill statistics: total plants count, total log entries count, current logging streak in days, and challenges won count.
- Status: Planned
- fulfills -> FEAT-030
- fulfills -> FEAT-022

## REQ-284: FR-S11-008 (Requirement)
The system shall display earned achievement badges in full colour and locked badges in greyscale with a padlock icon. Badge types shall include but are not limited to: "Hydro Master," "Balcony Boss," "Zero-Waste Gardener," and streak-based badges (e.g., "Streak: 30 Days").
- Status: Planned
- fulfills -> FEAT-030
- fulfills -> FEAT-022

## REQ-285: FR-S11-009 (Requirement)
Tapping any earned badge shall display a badge detail sheet showing: the badge graphic, the badge name, the date it was earned, the unlock criteria, and a Share button that opens MOD-12.
- Status: Planned
- fulfills -> FEAT-030
- fulfills -> FEAT-022

## REQ-286: FR-S11-010 (Requirement)
Tapping a locked badge shall display only the badge name and unlock criteria, with a progress indicator if applicable.
- Status: Planned
- fulfills -> FEAT-030
- fulfills -> FEAT-022

## REQ-287: FR-S11-011 (Requirement)
The system shall display a "My Skills" section showing the Confidence Score as a 15-skill chart or bar list. Tracked skills shall be method-agnostic (e.g., Watering, Nutrient Mixing, Pest ID, Pruning). This section shall be clearly labelled as optional.
- Status: Planned
- fulfills -> FEAT-030
- fulfills -> FEAT-022

## REQ-288: FR-S11-012 (Requirement)
Skill scores shall increment based on logged actions relevant to each skill (e.g., logging a "Feed" action increases the Nutrient Mixing skill).
- Status: Planned
- fulfills -> FEAT-030
- fulfills -> FEAT-022

## REQ-289: FR-S11-013 (Requirement)
The system shall display the current logging streak (consecutive days with at least one log entry) with a flame icon, and the user's longest streak as a personal record label.
- Status: Planned
- fulfills -> FEAT-030
- fulfills -> FEAT-022

## REQ-290: FR-S11-014 (Requirement)
The system shall display a 30-day calendar heatmap showing logging activity density per day.
- Status: Planned
- fulfills -> FEAT-030
- fulfills -> FEAT-022

## REQ-291: FR-S11-015 (Requirement)
The system shall display tappable navigation rows for: Progress Reels Gallery (→ SCR-15), Cemetery Log (→ SCR-14), and Creator Studio (→ SCR-16 with the label "Earn from your guides").
- Status: Planned
- fulfills -> FEAT-030
- fulfills -> FEAT-022

## REQ-292: FR-S11-016 (Requirement)
The system shall display a referral banner showing: "Invite 3 friends → unlock Multi-Zone Management," a progress bar (X / 3 friends referred), and a "Share Invite Link" button that opens MOD-12 with the referral link as the shared content.
- Status: Planned
- fulfills -> FEAT-030
- fulfills -> FEAT-022

## REQ-293: FR-S11-017 (Requirement)
When a user has successfully referred 3 friends (verified by the referral link being used to install the app), the system shall unlock Multi-Zone Management and replace the referral banner with a "Multi-Zone Management unlocked ✓" confirmation card.
- Status: Planned
- fulfills -> FEAT-030
- fulfills -> FEAT-022

## REQ-294: FR-S11-018 (Requirement)
If the user has not purchased the Supporter Badge, the system shall display a subtle banner at the bottom of the Profile screen: "$2.99 · Remove interstitial ads" with a "Learn More" button that opens MOD-07 Supporter Badge Dialog.
- Status: Planned
- fulfills -> FEAT-030
- fulfills -> FEAT-022

## REQ-295: FR-S11-019 (Requirement)
If the user has purchased the Supporter Badge, the banner shall be replaced by a "Supporter ✓" badge on their profile header card.
- Status: Planned
- fulfills -> FEAT-030
- fulfills -> FEAT-022

## REQ-296: FR-S12-001 (Requirement)
The system shall navigate to Settings from the Settings icon on SCR-11 Profile and from the Settings icon on SCR-01 Dashboard header.
- Status: Planned
- fulfills -> FEAT-019
- fulfills -> FEAT-027
- fulfills -> FEAT-036

## REQ-297: FR-S12-002 (Requirement)
A back arrow shall return the user to the previous screen.
- Status: Planned
- fulfills -> FEAT-019
- fulfills -> FEAT-027
- fulfills -> FEAT-036

## REQ-298: FR-S12-003 (Requirement)
The system shall provide an editable display name field and a growing method multi-select (allowing multiple methods to be active simultaneously).
- Status: Planned
- fulfills -> FEAT-019
- fulfills -> FEAT-027
- fulfills -> FEAT-036

## REQ-299: FR-S12-004 (Requirement)
The system shall provide an editable location/zone field with an auto-detect button and a manual entry fallback.
- Status: Planned
- fulfills -> FEAT-019
- fulfills -> FEAT-027
- fulfills -> FEAT-036

## REQ-300: FR-S12-005 (Requirement)
The system shall provide a unit system selector: Metric and Imperial. Changing this shall immediately update all numeric values displayed throughout the app.
- Status: Planned
- fulfills -> FEAT-019
- fulfills -> FEAT-027
- fulfills -> FEAT-036

## REQ-301: FR-S12-006 (Requirement)
The system shall provide a "Notification Preferences →" row that opens MOD-10 Notification Preferences Sheet.
- Status: Planned
- fulfills -> FEAT-019
- fulfills -> FEAT-027
- fulfills -> FEAT-036

## REQ-302: FR-S12-007 (Requirement)
The system shall provide a theme toggle with two options: Balcony Bright (light mode) and Grow Tent Dark (dark mode).
- Status: Planned
- fulfills -> FEAT-019
- fulfills -> FEAT-027
- fulfills -> FEAT-036

## REQ-303: FR-S12-008 (Requirement)
The system shall provide a font selector with at minimum two options: Standard and Dyslexia-Friendly (OpenDyslexic or equivalent). Selecting Dyslexia-Friendly shall apply the font across all text in the app immediately.
- Status: Planned
- fulfills -> FEAT-019
- fulfills -> FEAT-027
- fulfills -> FEAT-036

## REQ-304: FR-S12-009 (Requirement)
The system shall provide a Colour-Blind Mode toggle. When enabled, all health status indicators and metric colour codings shall switch to a high-contrast palette accessible to users with common colour vision deficiencies.
- Status: Planned
- fulfills -> FEAT-019
- fulfills -> FEAT-027
- fulfills -> FEAT-036

## REQ-305: FR-S12-010 (Requirement)
The system shall provide a text size slider allowing the user to adjust the base text size across the app.
- Status: Planned
- fulfills -> FEAT-019
- fulfills -> FEAT-027
- fulfills -> FEAT-036

## REQ-306: FR-S12-011 (Requirement)
The system shall provide a Voice Input toggle. When enabled, a microphone icon shall be surfaced on all text input fields throughout the app, allowing hands-free entry.
- Status: Planned
- fulfills -> FEAT-019
- fulfills -> FEAT-027
- fulfills -> FEAT-036

## REQ-307: FR-S12-012 (Requirement)
The system shall provide a Screen Reader Mode toggle. When enabled, the system shall optimise all interactive element labels and focus order for VoiceOver (iOS) and TalkBack (Android).
- Status: Planned
- fulfills -> FEAT-019
- fulfills -> FEAT-027
- fulfills -> FEAT-036

## REQ-308: FR-S12-014 (Requirement)
The system shall provide a language selector with at minimum English and German at launch. Changing language shall restart the app and apply the new locale to all UI text.
- Status: Planned
- fulfills -> FEAT-019
- fulfills -> FEAT-027
- fulfills -> FEAT-036

## REQ-309: FR-S12-015 (Requirement)
The system shall provide a date format selector: DD/MM/YYYY or MM/DD/YYYY.
- Status: Planned
- fulfills -> FEAT-019
- fulfills -> FEAT-027
- fulfills -> FEAT-036

## REQ-310: FR-S12-016 (Requirement)
The system shall provide a "Privacy Dashboard →" row that navigates to SCR-13.
- Status: Planned
- fulfills -> FEAT-019
- fulfills -> FEAT-027
- fulfills -> FEAT-036

## REQ-311: FR-S12-017 (Requirement)
The system shall provide a "Do Not Sell My Info" toggle (CCPA compliance). Enabling it shall immediately disable all ad personalisation data collection.
- Status: Planned
- fulfills -> FEAT-019
- fulfills -> FEAT-027
- fulfills -> FEAT-036

## REQ-312: FR-S12-018 (Requirement)
The system shall provide an Ad Personalisation toggle. Disabling it shall suppress personalised ad targeting without removing ads from the app.
- Status: Planned
- fulfills -> FEAT-019
- fulfills -> FEAT-027
- fulfills -> FEAT-036

## REQ-313: FR-S12-019 (Requirement)
The system shall provide a Community Data opt-in toggle for contributing anonymized grow data to the Local Grow Map and Community Hub stats. Disabling it shall remove the user's data from all aggregate calculations.
- Status: Planned
- fulfills -> FEAT-019
- fulfills -> FEAT-027
- fulfills -> FEAT-036

## REQ-314: FR-S12-020 (Requirement)
The system shall provide a "Supporter Badge — Remove Ads" row that opens MOD-07 Supporter Badge Dialog.
- Status: Planned
- fulfills -> FEAT-019
- fulfills -> FEAT-027
- fulfills -> FEAT-036

## REQ-315: FR-S12-021 (Requirement)
The system shall provide a "Show contextual learning tips" toggle. When disabled, the system shall suppress all contextual tip cards on SCR-01 Dashboard and SCR-03 Plant Detail.
- Status: Planned
- fulfills -> FEAT-019
- fulfills -> FEAT-027
- fulfills -> FEAT-036

## REQ-316: FR-S12-022 (Requirement)
The system shall provide an "Offline article caching" toggle. When enabled, the system shall download all Smart Tips Library articles over Wi-Fi when connected, making them available offline.
- Status: Planned
- fulfills -> FEAT-019
- fulfills -> FEAT-027
- fulfills -> FEAT-036

## REQ-317: FR-S12-023 (Requirement)
The About section shall display the current app version string.
- Status: Planned
- fulfills -> FEAT-019
- fulfills -> FEAT-027
- fulfills -> FEAT-036

## REQ-318: FR-S12-024 (Requirement)
The About section shall provide tappable links to: Terms of Service, Privacy Policy, Rate GardenPulse (opens the respective App Store / Play Store rating page), and Send Feedback.
- Status: Planned
- fulfills -> FEAT-019
- fulfills -> FEAT-027
- fulfills -> FEAT-036

## REQ-319: FR-S12-025 (Requirement)
The system shall provide an "Export All My Data" button that initiates a GDPR-compliant data export. The system shall notify the user that the export will be delivered within 24 hours (e.g., downloaded or emailed to a confirmed address).
- Status: Planned
- fulfills -> FEAT-019
- fulfills -> FEAT-027
- fulfills -> FEAT-036

## REQ-320: FR-S12-027 (Requirement)
The system shall provide a "Sign Out" button that clears the local session while retaining cached plant data, allowing the user to re-enter the app without re-onboarding.
- Status: Planned
- fulfills -> FEAT-019
- fulfills -> FEAT-027
- fulfills -> FEAT-036

## REQ-321: FR-S13-001 (Requirement)
The system shall navigate to the Privacy Dashboard from the "Privacy & Data" section in SCR-12 Settings.
- Status: Planned
- fulfills -> FEAT-019

## REQ-322: FR-S13-002 (Requirement)
A back arrow shall return the user to SCR-12.
- Status: Planned
- fulfills -> FEAT-019

## REQ-323: FR-S13-003 (Requirement)
The screen shall display a "Last updated [timestamp]" label in the header showing when the privacy settings were last modified.
- Status: Planned
- fulfills -> FEAT-019

## REQ-324: FR-S13-005 (Requirement)
The data inventory shall cover at minimum the following categories: Location Data, Plant Logs, Photos, Voice Logs, and Ad Personalisation Data.
- Status: Planned
- fulfills -> FEAT-019

## REQ-325: FR-S13-006 (Requirement)
Each data category row shall provide a "Clear" or "Delete All" button that immediately deletes all data in that category after a single confirmation tap.
- Status: Planned
- fulfills -> FEAT-019

## REQ-326: FR-S13-007 (Requirement)
The Plant Logs category row shall additionally provide an "Export" button that triggers the data export flow for log data only.
- Status: Planned
- fulfills -> FEAT-019

## REQ-327: FR-S13-008 (Requirement)
The system shall provide granular on/off toggles for each of the following: Location Sharing, Photo Storage, Voice Log Retention, Ad Personalisation, and Community Anonymised Data Contribution. Each toggle shall have a one-sentence description of what it controls.
- Status: Planned
- fulfills -> FEAT-019

## REQ-328: FR-S13-009 (Requirement)
Disabling any toggle shall take effect immediately and persist across app restarts.
- Status: Planned
- fulfills -> FEAT-019

## REQ-329: FR-S13-010 (Requirement)
Disabling Community Anonymised Data Contribution shall remove the user's aggregate data from the Local Grow Map and all community stats within 24 hours.
- Status: Planned
- fulfills -> FEAT-019

## REQ-330: FR-S13-011 (Requirement)
The system shall display a prominent "Export My Data" CTA button (GDPR Art. 20 — data portability). Tapping it shall initiate the export process and display a status card: "Your data export is being prepared — ready within 24 hours."
- Status: Planned
- fulfills -> FEAT-019

## REQ-331: FR-S13-012 (Requirement)
The system shall display a "Delete All My Data" CTA button styled in red (GDPR Art. 17 — right to erasure). This shall trigger the same two-step confirmation as in SCR-12.
- Status: Planned
- fulfills -> FEAT-019

## REQ-332: FR-S13-013 (Requirement)
The system shall display a prominent "Do Not Sell My Info" toggle (CCPA Section 1798.120). This shall be visually distinct and easy to locate.
- Status: Planned
- fulfills -> FEAT-019

## REQ-333: FR-S13-014 (Requirement)
The system shall display a tappable Privacy Policy link and a tappable Data Processing Agreements summary link.
- Status: Planned
- fulfills -> FEAT-019

## REQ-334: FR-S14-001 (Requirement)
The system shall navigate to the Cemetery Log from SCR-11 Profile navigation links and from the Archive confirmation dialog on SCR-03 Plant Detail.
- Status: Planned
- fulfills -> FEAT-016

## REQ-335: FR-S14-002 (Requirement)
A back arrow shall return the user to the originating screen.
- Status: Planned
- fulfills -> FEAT-016

## REQ-336: FR-S14-003 (Requirement)
A "+ Add" button in the header shall allow the user to manually add a plant that died before the app was in use, without requiring a prior log history.
- Status: Planned
- fulfills -> FEAT-016

## REQ-337: FR-S14-004 (Requirement)
When the Cemetery Log contains two or more archived plants with the same cause of death, the system shall display a dismissible insight card at the top of the log: "Pattern detected: You've lost [N] plants to [cause] → Check your [relevant screen]." The suggested screen shall be contextual (e.g., overwatering → link to SCR-07 Smart Scheduler).
- Status: Planned
- fulfills -> FEAT-016

## REQ-338: FR-S14-005 (Requirement)
When the Cemetery Log is empty, the system shall display an empty state with an illustrated gravestone graphic and the label "No failures recorded yet — keep growing! 🌱."
- Status: Planned
- fulfills -> FEAT-016

## REQ-339: FR-S14-006 (Requirement)
Each archived plant entry shall display: plant thumbnail, plant name, growing method badge, date archived, and a "cause of death" label.
- Status: Planned
- fulfills -> FEAT-016

## REQ-340: FR-S14-007 (Requirement)
The cause of death shall be editable via a selector with pre-defined categories: pH Spike, Root Rot, Overwatering, Underwatering, Nutrient Burn, Pest, Light Stress, Temperature Shock, and Unknown.
- Status: Planned
- fulfills -> FEAT-016

## REQ-341: FR-S14-008 (Requirement)
Each entry shall include an editable "What I learned:" text field with a voice input microphone icon. Notes saved here shall be timestamped.
- Status: Planned
- fulfills -> FEAT-016

## REQ-342: FR-S14-009 (Requirement)
The Cemetery Log shall be filterable by: Method, Date, and Cause.
- Status: Planned
- fulfills -> FEAT-016

## REQ-343: FR-S14-010 (Requirement)
Each entry shall provide a "Restore to Garden" button. Tapping it shall move the plant back to SCR-02 Plant List as an active plant, with all its original log history intact.
- Status: Planned
- fulfills -> FEAT-016

## REQ-344: FR-S14-011 (Requirement)
Each entry shall provide a "Delete Entry" icon. Tapping it shall display a confirmation dialog before permanently deleting the entry.
- Status: Planned
- fulfills -> FEAT-016

## REQ-345: FR-S14-012 (Requirement)
A "+ Log Manually" CTA button shall open an inline form with fields for: plant name, growing method, estimated date of archival, cause of death (selector), and notes.
- Status: Planned
- fulfills -> FEAT-016

## REQ-346: FR-S14-013 (Requirement)
The system shall provide an "Export Log as PDF" button. Tapping it shall trigger MOD-05 Rewarded Video Prompt. After successful video completion, MOD-12 Export / Share Sheet shall open with the Cemetery Log PDF as the export content.
- Status: Planned
- fulfills -> FEAT-016

## REQ-347: FR-S16-001 (Requirement)
The system shall navigate to the Creator Studio from the "Creator Studio" row on SCR-11 Profile.
- Status: Planned
- fulfills -> FEAT-035

## REQ-348: FR-S16-002 (Requirement)
A back arrow shall return the user to SCR-11.
- Status: Planned
- fulfills -> FEAT-035

## REQ-349: FR-S16-003 (Requirement)
The "Publish" button in the header shall be disabled (greyed) until the guide has passed a pre-publication readiness check: title present, at least one category selected, and body content exceeding a minimum character count.
- Status: Planned
- fulfills -> FEAT-035

## REQ-350: FR-S16-004 (Requirement)
The system shall display a revenue info banner at the top of the Creator Studio: "Write guides → earn AdMob revenue share," and a moderation notice: "All guides reviewed before going live (24–48 h)."
- Status: Planned
- fulfills -> FEAT-035

## REQ-351: FR-S16-005 (Requirement)
The system shall provide a "Learn How It Works" link in the banner that opens a brief inline explanation of the creator revenue share model.
- Status: Planned
- fulfills -> FEAT-035

## REQ-352: FR-S16-006 (Requirement)
The system shall provide a cover image upload area. Tapping it shall offer options: capture with camera (triggers MOD-04 if camera permission not granted) or upload from the photo library.
- Status: Planned
- fulfills -> FEAT-035

## REQ-353: FR-S16-007 (Requirement)
The system shall provide a guide title text field with a maximum of 80 characters.
- Status: Planned
- fulfills -> FEAT-035

## REQ-354: FR-S16-008 (Requirement)
The system shall provide a category / method multi-select using chips. Available categories shall include: Soil, Hydro, Container, Indoor, Microgreen, Pest Control, Nutrition, and all other growing methods supported by the app.
- Status: Planned
- fulfills -> FEAT-035

## REQ-355: FR-S16-009 (Requirement)
The system shall provide a tags field accepting a maximum of 5 tags, with autocomplete suggestions from the app's tag library.
- Status: Planned
- fulfills -> FEAT-035

## REQ-356: FR-S16-010 (Requirement)
The system shall provide a rich text editor with a formatting toolbar: Bold, Italic, Heading (H2, H3), Bullet List, Numbered List, Image Insert, and Divider.
- Status: Planned
- fulfills -> FEAT-035

## REQ-357: FR-S16-011 (Requirement)
The editor shall provide an "Insert Plant Template" shortcut button that inserts a standardised plant care table template (with rows for Watering, Light, Nutrients, Common Issues) at the cursor position.
- Status: Planned
- fulfills -> FEAT-035

## REQ-358: FR-S16-012 (Requirement)
The editor shall provide an "Insert Tip Block" shortcut button that inserts a styled callout block (visually distinct box for tips or warnings) at the cursor position.
- Status: Planned
- fulfills -> FEAT-035

## REQ-359: FR-S16-013 (Requirement)
The system shall calculate and display an estimated read time label that updates live as the user writes.
- Status: Planned
- fulfills -> FEAT-035

## REQ-360: FR-S16-014 (Requirement)
The system shall provide a "Preview" toggle that switches the editor to a read-view, showing the guide exactly as it will appear to readers.
- Status: Planned
- fulfills -> FEAT-035

## REQ-361: FR-S16-015 (Requirement)
The system shall provide a "Save Draft" button that saves the current guide locally and syncs it when the device is connected.
- Status: Planned
- fulfills -> FEAT-035

## REQ-362: FR-S16-016 (Requirement)
The system shall provide a "Submit for Review" CTA button. Tapping it shall display a confirmation dialog: "Submit for moderation? Your guide will be reviewed in 24–48 hours." On confirmation, the guide shall be sent for review and its status set to "Under Review."
- Status: Planned
- fulfills -> FEAT-035

## REQ-363: FR-S16-017 (Requirement)
The system shall display a "My Published Guides" section below the editor area, listing all of the user's guides with: thumbnail, title, status chip (Under Review / Live / Rejected), and for Live guides: view count and ad revenue earned label.
- Status: Planned
- fulfills -> FEAT-035

## REQ-364: FR-M01-001 (Requirement)
The Quick Log Sheet shall be triggered by: the "+" FAB on SCR-01 Dashboard, the "+" FAB on SCR-02 Plant List, the "Log" FAB on SCR-03 Plant Detail, the "Log" action pill on SCR-03, and the "Submit Entry" button on community challenges.
- Status: Planned
- fulfills -> FEAT-017

## REQ-365: FR-M01-002 (Requirement)
The sheet shall open as a bottom sheet with an initial snap height of approximately 50% of screen height, expandable to approximately 80% via drag.
- Status: Planned
- fulfills -> FEAT-017

## REQ-366: FR-M01-003 (Requirement)
Tapping outside the sheet or dragging it downward shall dismiss it without saving any data.
- Status: Planned
- fulfills -> FEAT-017

## REQ-367: FR-M01-004 (Requirement)
The sheet shall display a horizontal scrollable list of the user's active plants as thumbnail cards. If the sheet was opened from SCR-03 Plant Detail, the originating plant shall be pre-selected.
- Status: Planned
- fulfills -> FEAT-017

## REQ-368: FR-M01-005 (Requirement)
Selecting a plant shall highlight its card with a selection ring. At least one plant must be selected before the "Log It" button is enabled.
- Status: Planned
- fulfills -> FEAT-017

## REQ-369: FR-M01-006 (Requirement)
The sheet shall display a large photo capture area. Tapping it shall open the native camera (triggering MOD-04 if camera permission is not granted). A gallery import icon shall allow the user to select an existing photo instead.
- Status: Planned
- fulfills -> FEAT-017

## REQ-370: FR-M01-007 (Requirement)
A photo is optional. The user shall be able to log an entry without capturing a photo.
- Status: Planned
- fulfills -> FEAT-017

## REQ-371: FR-M01-008 (Requirement)
The sheet shall display activity type chips (multi-select): Water, Feed, Prune, Check, Harvest, Repot, Transplant, Note. At least one activity type must be selected before the "Log It" button is enabled.
- Status: Planned
- fulfills -> FEAT-017

## REQ-372: FR-M01-009 (Requirement)
The sheet shall display a single emoji-scale slider from 1 (😟) to 5 (😄) labelled "How did it go?" The slider shall default to the midpoint (3). Rating is optional.
- Status: Planned
- fulfills -> FEAT-017

## REQ-373: FR-M01-010 (Requirement)
The sheet shall display a freeform "Add a quick note…" text area with a microphone icon. Tapping the microphone icon shall request mic permission if not granted (MOD-04), then open voice recording. The recorded audio shall be transcribed to text and placed in the notes field.
- Status: Planned
- fulfills -> FEAT-017

## REQ-374: FR-M01-011 (Requirement)
The system shall NEVER auto-activate the microphone. It shall only activate on explicit user tap of the mic icon.
- Status: Planned
- fulfills -> FEAT-017

## REQ-375: FR-M01-012 (Requirement)
The sheet shall display an auto-generated location tag chip (e.g., "Berlin · Zone 7b"). The user shall be able to remove the tag by tapping the "×" icon on the chip.
- Status: Planned
- fulfills -> FEAT-017

## REQ-376: FR-M01-013 (Requirement)
The sheet shall display an "Add to Reel" toggle. When enabled, the logged photo shall be included in the timelapse sequence for the selected plant and will be available for reel generation in SCR-15.
- Status: Planned
- fulfills -> FEAT-017

## REQ-377: FR-M01-014 (Requirement)
The sheet shall include a collapsed "Add metrics (optional)" row. When expanded, it shall reveal: a pH slider, an EC/PPM numeric field, a Moisture % field, and a Temperature field. All metric fields shall be optional.
- Status: Planned
- fulfills -> FEAT-017

## REQ-378: FR-M01-015 (Requirement)
The "Log It ✓" button shall be enabled only when at least one plant and one activity type are selected. Tapping it shall save the log entry, update the selected plant's last logged timestamp, and update the Garden Health Score based on the logged activity. The sheet shall close with a brief success animation.
- Status: Planned
- fulfills -> FEAT-017

## REQ-379: FR-M02-001 (Requirement)
The Add / Edit Plant Sheet shall be triggered by: the "+" button on SCR-02 Plant List, the "Add Your First Plant" button during onboarding, and the "Edit Plant" option in SCR-03 Plant Detail's overflow menu.
- Status: Planned
- fulfills -> FEAT-017

## REQ-380: FR-M02-002 (Requirement)
When triggered from SCR-03 for editing, all fields shall be pre-filled with the existing plant's data.
- Status: Planned
- fulfills -> FEAT-017

## REQ-381: FR-M02-003 (Requirement)
Tapping "Cancel" or swiping the sheet down shall dismiss without saving. If unsaved changes are present, a confirmation dialog shall ask "Discard changes?"
- Status: Planned
- fulfills -> FEAT-017

## REQ-382: FR-M02-004 (Requirement)
The sheet shall display a plant name search field with autocomplete sourced from the local plant database (minimum 3,000 species). The autocomplete list shall appear as the user types from 2 characters onward.
- Status: Planned
- fulfills -> FEAT-017

## REQ-383: FR-M02-005 (Requirement)
The sheet shall provide a "Scan to identify" camera button. If camera permission is not granted, MOD-04 (Camera) shall be triggered first. On successful plant identification via camera, the species name and photo shall be auto-filled.
- Status: Planned
- fulfills -> FEAT-017

## REQ-384: FR-M02-006 (Requirement)
The sheet shall provide browse-by-type category chips: Herb, Vegetable, Fruit, Flower, Houseplant, Microgreen. Tapping a chip shall filter the autocomplete suggestions.
- Status: Planned
- fulfills -> FEAT-017

## REQ-385: FR-M02-007 (Requirement)
The sheet shall provide a plant photo capture / gallery import area. The selected photo shall be used as the plant's thumbnail throughout the app.
- Status: Planned
- fulfills -> FEAT-017

## REQ-386: FR-M02-008 (Requirement)
The sheet shall provide a nickname field with a maximum of 30 characters.
- Status: Planned
- fulfills -> FEAT-017

## REQ-387: FR-M02-009 (Requirement)
The sheet shall provide a required growing method selector with pills: Soil, Container, Hydro, Indoor.
- Status: Planned
- fulfills -> FEAT-017

## REQ-388: FR-M02-010 (Requirement)
The sheet shall provide a conditional container/pot size field (shown only when the Container method is selected), with a numeric field and a unit toggle (L / gal).
- Status: Planned
- fulfills -> FEAT-017

## REQ-389: FR-M02-011 (Requirement)
The sheet shall display the auto-detected zone badge. A "Change location" link shall allow the user to manually enter a different location for this specific plant.
- Status: Planned
- fulfills -> FEAT-017

## REQ-390: FR-M02-012 (Requirement)
The sheet shall provide a started date picker (date selector, defaults to today) and an optional target harvest date picker.
- Status: Planned
- fulfills -> FEAT-017

## REQ-391: FR-M02-013 (Requirement)
The sheet shall provide a "Remind me for this plant" toggle. When enabled, the plant's care tasks shall generate notifications per the user's notification preferences.
- Status: Planned
- fulfills -> FEAT-017

## REQ-392: FR-M02-014 (Requirement)
The "Save Plant" button shall be enabled only when the plant name field is non-empty and a growing method is selected.
- Status: Planned
- fulfills -> FEAT-017

## REQ-393: FR-M02-015 (Requirement)
On save, if this is a new plant, the system shall add the plant to SCR-02 Plant List and navigate to SCR-03 Plant Detail for the new plant. If this is an edit, the updated data shall be reflected immediately on SCR-03.
- Status: Planned
- fulfills -> FEAT-017

## REQ-394: FR-M03-001 (Requirement)
The QR Scanner Overlay shall be triggered by: the "QR / Label Scanner" card on SCR-04 Tools Hub, and the "Scan label" button on SCR-05 Nutrient / Recipe Calculator.
- Status: Planned
- fulfills -> FEAT-013

## REQ-395: FR-M03-002 (Requirement)
A "✕ Close" button in the top-left shall dismiss the overlay and return the user to the triggering screen without any data change.
- Status: Planned
- fulfills -> FEAT-013

## REQ-396: FR-M03-003 (Requirement)
The overlay shall display a full-screen live camera feed. If camera permission has not been granted, MOD-04 (Permission Context Modal — Camera) shall be triggered before the camera UI is shown.
- Status: Planned
- fulfills -> FEAT-013

## REQ-397: FR-M03-004 (Requirement)
The overlay shall display an animated scan frame (rectangle with pulsing border) as a visual alignment guide for QR codes and barcodes.
- Status: Planned
- fulfills -> FEAT-013

## REQ-398: FR-M03-005 (Requirement)
The overlay shall display a "Point at a QR code or barcode" instruction label.
- Status: Planned
- fulfills -> FEAT-013

## REQ-399: FR-M03-006 (Requirement)
The overlay shall provide a flash/torch toggle icon.
- Status: Planned
- fulfills -> FEAT-013

## REQ-400: FR-M03-007 (Requirement)
The overlay shall provide a "Enter code manually" fallback text link at the bottom of the screen for situations where a physical scan is not possible.
- Status: Planned
- fulfills -> FEAT-013

## REQ-401: FR-M03-008 (Requirement)
Upon successful detection of a QR code or barcode, the system shall check the detected value against the local brand/product database.
- Status: Planned
- fulfills -> FEAT-013

## REQ-402: FR-M03-009 (Requirement)
When a match is found, the system shall display a bottom sheet card showing: product thumbnail (if available), product name, brand name, and product type chip (Nutrient / Seed / Sensor / Other).
- Status: Planned
- fulfills -> FEAT-013

## REQ-403: FR-M03-010 (Requirement)
The success card shall provide contextual action buttons based on the triggering screen: "Fill Calculator →" (if triggered from SCR-05, auto-fills the brand selector) or "Log Scan →" (creates a scan log entry for the current plant).
- Status: Planned
- fulfills -> FEAT-013

## REQ-404: FR-M03-011 (Requirement)
When no match is found in the local database, the system shall display the raw decoded value and a "Log Scan →" button with no auto-fill.
- Status: Planned
- fulfills -> FEAT-013

## REQ-405: FR-M04-001 (Requirement)
The Permission Context Modal shall be triggered contextually — never at app launch or during onboarding unless the user explicitly initiates an action requiring the permission. Variants shall exist for: Location, Camera, and Microphone.
- Status: Planned
- fulfills -> FEAT-014

## REQ-406: FR-M04-002 (Requirement)
The Location variant shall be triggered after the user taps "Next" on ONB-2 and before navigating to ONB-3.
- Status: Planned
- fulfills -> FEAT-014

## REQ-407: FR-M04-003 (Requirement)
The Camera variant shall be triggered the first time the user taps any camera-dependent feature: Leaf Diagnostics, QR Scanner, photo capture in Quick Log, or "Scan to identify" in MOD-02.
- Status: Planned
- fulfills -> FEAT-014

## REQ-408: FR-M04-004 (Requirement)
The Microphone variant shall be triggered only when the user explicitly taps a microphone / voice input icon.
- Status: Planned
- fulfills -> FEAT-014

## REQ-409: FR-M04-005 (Requirement)
The modal shall display a contextual illustration relevant to the permission type: a map pin with leaf (location), a camera lens with leaf (camera), a microphone with waveform (microphone).
- Status: Planned
- fulfills -> FEAT-014

## REQ-410: FR-M04-006 (Requirement)
The modal shall display a title and a two-sentence benefit description explaining what the permission enables and how the data is used (e.g., "GardenPulse uses your location to give weather-aware care tips. You can change this any time in Settings.").
- Status: Planned
- fulfills -> FEAT-014

## REQ-411: FR-M04-007 (Requirement)
The modal shall display a privacy reassurance label (e.g., "Location never shared publicly without explicit opt-in").
- Status: Planned
- fulfills -> FEAT-014

## REQ-412: FR-M04-008 (Requirement)
The primary "Allow [Permission]" button shall trigger the native OS system permission dialog. The modal shall close after the OS dialog is dismissed (regardless of grant or denial).
- Status: Planned
- fulfills -> FEAT-014

## REQ-413: FR-M04-009 (Requirement)
The "Not Now" secondary link shall dismiss the modal without triggering the OS permission dialog. The originating feature shall gracefully degrade (e.g., show the manual location entry fallback).
- Status: Planned
- fulfills -> FEAT-014

## REQ-414: FR-M04-010 (Requirement)
A "Learn more about privacy →" text link shall navigate to SCR-13 Privacy Dashboard.
- Status: Planned
- fulfills -> FEAT-014

## REQ-415: FR-M04-011 (Requirement)
If the user has previously denied a permission at the OS level and then triggers a feature requiring it, the system shall display a non-modal banner (not a full modal) reading "[Permission] access is off" with an "Open Settings" button that deep-links to the device's permission settings for the app.
- Status: Planned
- fulfills -> FEAT-014

## REQ-416: FR-M04-012 (Requirement)
For the camera-denied state specifically, the system shall also display a "Use Gallery Instead" fallback button that opens the device photo library.
- Status: Planned
- fulfills -> FEAT-014

## REQ-417: FR-M05-001 (Requirement)
The Rewarded Video Prompt shall be triggered by: the "Export / Share" button on SCR-05 Nutrient / Recipe Calculator results, the "Download" button on SCR-15 Progress Reels Gallery playback, and the "Export Log as PDF" button on SCR-14 Cemetery Log.
- Status: Planned
- fulfills -> FEAT-025

## REQ-418: FR-M05-002 (Requirement)
The prompt shall display a video play icon graphic, a heading "Unlock [X]" (where X is the specific unlock: "PDF Export," "HD Download," or "Compliance Log"), a sub-label "Watch a 30-second video to unlock this for free," and an estimated duration label ("~30 seconds").
- Status: Planned
- fulfills -> FEAT-025

## REQ-419: FR-M05-003 (Requirement)
The prompt shall display a "▶ Watch Video" primary button and a "No Thanks" secondary text link.
- Status: Planned
- fulfills -> FEAT-025

## REQ-420: FR-M05-004 (Requirement)
Tapping "No Thanks" shall dismiss the prompt and return the user to the triggering screen without providing the unlock.
- Status: Planned
- fulfills -> FEAT-025

## REQ-421: FR-M05-005 (Requirement)
Tapping "Watch Video" shall launch the AdMob rewarded video unit in full-screen.
- Status: Planned
- fulfills -> FEAT-025

## REQ-422: FR-M05-006 (Requirement)
The video player shall display a progress timer label and a skip button that appears only after the required minimum watch time has elapsed (as defined by the AdMob rewarded unit configuration).
- Status: Planned
- fulfills -> FEAT-025

## REQ-423: FR-M05-007 (Requirement)
After the video completes (or skip is allowed and tapped), the system shall display an unlock success state with: an animated unlock visual, the label "Unlocked! Your [X] is ready," and a "Download / Export Now" CTA button.
- Status: Planned
- fulfills -> FEAT-025

## REQ-424: FR-M05-008 (Requirement)
Tapping "Download / Export Now" shall open MOD-12 Export / Share Sheet with the unlocked content ready.
- Status: Planned
- fulfills -> FEAT-025

## REQ-425: FR-M05-009 (Requirement)
The success state shall auto-dismiss after 3 seconds if the user does not tap the CTA.
- Status: Planned
- fulfills -> FEAT-025

## REQ-426: FR-M06-001 (Requirement)
The Interstitial Ad shall be triggered ONLY when the user taps "Generate Recipe" on SCR-05 Nutrient / Recipe Calculator. It shall appear during the 1.5-second animated loading state between tapping the button and the results appearing.
- Status: Planned
- fulfills -> FEAT-023

## REQ-427: FR-M06-002 (Requirement)
The Interstitial Ad SHALL NEVER be triggered on: any onboarding screen (ONB-1 through ONB-4), any permission request screen (MOD-04), any error state, or any screen where the user is in the process of granting or reviewing permissions.
- Status: Planned
- fulfills -> FEAT-023

## REQ-428: FR-M06-003 (Requirement)
The system shall display the AdMob interstitial unit full-screen with an attribution label "Ad · Powered by AdMob."
- Status: Planned
- fulfills -> FEAT-023

## REQ-429: FR-M06-004 (Requirement)
A "✕ Close" button shall appear after a minimum of 5 seconds, complying with AdMob interstitial policy. Tapping it shall dismiss the ad and display the calculator results.
- Status: Planned
- fulfills -> FEAT-023

## REQ-430: FR-M06-005 (Requirement)
When a user has purchased the Supporter Badge (MOD-07), the Interstitial Ad trigger on SCR-05 shall be suppressed entirely. The results shall appear directly after the 1.5-second loading animation with no ad shown.
- Status: Planned
- fulfills -> FEAT-023

## REQ-431: FR-M07-001 (Requirement)
The Supporter Badge Dialog shall be triggered by: the "Supporter Badge — Remove Ads" row in SCR-12 Settings, and the "Learn More" button on the profile supporter banner in SCR-11.
- Status: Planned
- fulfills -> FEAT-027

## REQ-432: FR-M07-002 (Requirement)
The dialog shall display the Supporter Badge graphic with an animated shimmer, the heading "Support GardenPulse 🌿," and the price label "$2.99 · One-time · No subscription."
- Status: Planned
- fulfills -> FEAT-027

## REQ-433: FR-M07-003 (Requirement)
The dialog shall display a "What you get" list: Remove interstitial ads forever, Supporter badge on your profile, GardenPulse watermark removal on exports.
- Status: Planned
- fulfills -> FEAT-027

## REQ-434: FR-M07-004 (Requirement)
The dialog shall display a "What stays" note in grey text: "Tips and native content remain — they help us improve the app." This is required to ensure the user understands that native ads will still appear.
- Status: Planned
- fulfills -> FEAT-027

## REQ-435: FR-M07-005 (Requirement)
Tapping the "Support GardenPulse — $2.99" button shall initiate the platform's native in-app purchase flow (App Store / Google Play Store billing).
- Status: Planned
- fulfills -> FEAT-027

## REQ-436: FR-M07-006 (Requirement)
On successful purchase, the system shall permanently record the Supporter Badge status, suppress all future interstitial ad triggers, and display the Supporter Badge on the user's profile header.
- Status: Planned
- fulfills -> FEAT-027

## REQ-437: FR-M07-007 (Requirement)
The dialog shall display a "Restore Purchase" link. Tapping it shall query the platform's purchase restoration API and re-apply the Supporter Badge if a prior purchase is found.
- Status: Planned
- fulfills -> FEAT-027

## REQ-438: FR-M07-008 (Requirement)
Tapping "Not Now" shall dismiss the dialog without initiating any purchase flow.
- Status: Planned
- fulfills -> FEAT-027

## REQ-439: FR-M08-001 (Requirement)
The Batch Mode Overlay shall be activated by the batch mode toggle button in the SCR-02 Plant List header.
- Status: Planned
- fulfills -> FEAT-018

## REQ-440: FR-M08-002 (Requirement)
Activating batch mode shall transform all plant cards in SCR-02 to show multi-select checkboxes without navigating away from the list.
- Status: Planned
- fulfills -> FEAT-018

## REQ-441: FR-M08-003 (Requirement)
The system shall replace the SCR-02 header with a batch mode header showing: a "Batch Mode" label, a selected count badge (e.g., "3 selected"), a "Select All" button, and a "✕ Cancel" button.
- Status: Planned
- fulfills -> FEAT-018

## REQ-442: FR-M08-004 (Requirement)
Tapping "Select All" shall select all plants currently visible in the list (respecting any active method filter).
- Status: Planned
- fulfills -> FEAT-018

## REQ-443: FR-M08-005 (Requirement)
When one or more plants are selected, the system shall display a bottom action bar with the following buttons: Water All, Feed All, Log Entry, and Archive.
- Status: Planned
- fulfills -> FEAT-018

## REQ-444: FR-M08-006 (Requirement)
Tapping "Water All" shall display a confirmation dialog: "Mark [N] plants as watered today?" On confirmation, the system shall log a "Water" activity for each selected plant with the current timestamp and update each plant's care schedule accordingly.
- Status: Planned
- fulfills -> FEAT-018

## REQ-445: FR-M08-007 (Requirement)
Tapping "Feed All" shall display a confirmation dialog: "Log a Feed entry for [N] plants?" On confirmation, the system shall log a "Feed" activity for each selected plant.
- Status: Planned
- fulfills -> FEAT-018

## REQ-446: FR-M08-008 (Requirement)
Tapping "Log Entry" shall open MOD-01 Quick Log Sheet with the multi-plant mode active — the plant selector shall show all selected plants pre-checked.
- Status: Planned
- fulfills -> FEAT-018

## REQ-447: FR-M08-009 (Requirement)
Tapping "Archive" shall display a confirmation dialog: "Archive [N] plants to the Cemetery Log?" On confirmation, all selected plants shall be moved to SCR-14 Cemetery Log and removed from SCR-02.
- Status: Planned
- fulfills -> FEAT-018

## REQ-448: FR-M08-010 (Requirement)
Tapping "✕ Cancel" or tapping the batch mode toggle again shall exit batch mode, restore the standard plant card view, and deselect all plants without performing any action.
- Status: Planned
- fulfills -> FEAT-018

## REQ-449: FR-M09-001 (Requirement)
The Tip Article Reader Sheet shall be triggered by: the contextual tip card on SCR-01 Dashboard, the contextual tip card on SCR-03 Plant Detail, the tip link in SCR-06 Leaf Diagnostics results, and any "Read: [article title]" link within the app.
- Status: Planned
- fulfills -> FEAT-032
- fulfills -> FEAT-033
- fulfills -> FEAT-034
- fulfills -> FEAT-036

## REQ-450: FR-M09-002 (Requirement)
The sheet shall open as a bottom sheet, initially at approximately 50% screen height, draggable to full screen.
- Status: Planned
- fulfills -> FEAT-032
- fulfills -> FEAT-033
- fulfills -> FEAT-034
- fulfills -> FEAT-036

## REQ-451: FR-M09-003 (Requirement)
The sheet shall display: a header image (offline-cached), the article title, a meta row (method tag chip, estimated read time, author name if a Creator Studio guide, published date), and the article body in rich text.
- Status: Planned
- fulfills -> FEAT-032
- fulfills -> FEAT-033
- fulfills -> FEAT-034
- fulfills -> FEAT-036

## REQ-452: FR-M09-004 (Requirement)
Article body content shall be rendered from the locally cached Smart Tips Library. The system shall NOT load external webviews or external URLs for article content.
- Status: Planned
- fulfills -> FEAT-032
- fulfills -> FEAT-033
- fulfills -> FEAT-034
- fulfills -> FEAT-036

## REQ-453: FR-M09-005 (Requirement)
Article content shall NOT auto-play any video or audio.
- Status: Planned
- fulfills -> FEAT-032
- fulfills -> FEAT-033
- fulfills -> FEAT-034
- fulfills -> FEAT-036

## REQ-454: FR-M09-006 (Requirement)
The sheet shall display one native ad block within the article body, styled as a "Recommended Tool" card, non-interruptive to the reading flow. It shall not appear at the very top or bottom of the content.
- Status: Planned
- fulfills -> FEAT-032
- fulfills -> FEAT-033
- fulfills -> FEAT-034
- fulfills -> FEAT-036

## REQ-455: FR-M09-007 (Requirement)
The sheet shall display a "Related Articles" row at the bottom showing 2 articles with thumbnails and titles. Tapping them shall replace the current article content in the same sheet.
- Status: Planned
- fulfills -> FEAT-032
- fulfills -> FEAT-033
- fulfills -> FEAT-034
- fulfills -> FEAT-036

## REQ-456: FR-M09-008 (Requirement)
The sheet shall provide a bookmark icon. Tapping it shall save the article to a "Bookmarked Tips" collection accessible from within the sheet.
- Status: Planned
- fulfills -> FEAT-032
- fulfills -> FEAT-033
- fulfills -> FEAT-034
- fulfills -> FEAT-036

## REQ-457: FR-M09-009 (Requirement)
The sheet shall provide a Share icon that opens MOD-12 Export / Share Sheet with the article title and a deep link as the shared content.
- Status: Planned
- fulfills -> FEAT-032
- fulfills -> FEAT-033
- fulfills -> FEAT-034
- fulfills -> FEAT-036

## REQ-458: FR-M09-010 (Requirement)
The sheet shall provide a "Mark as Read ✓" button. Tapping it shall mark the article as read so it does not re-appear as a suggestion until the content is updated.
- Status: Planned
- fulfills -> FEAT-032
- fulfills -> FEAT-033
- fulfills -> FEAT-034
- fulfills -> FEAT-036

## REQ-459: FR-M10-001 (Requirement)
The Notification Preferences Sheet shall be triggered by the "Notification Preferences →" row in SCR-12 Settings and the "Notification preferences →" quick link in SCR-07 Smart Scheduler.
- Status: Planned
- fulfills -> FEAT-009

## REQ-460: FR-M10-002 (Requirement)
The sheet shall display a master "Enable all reminders" toggle at the top. When disabled, all per-category toggles shall be visually greyed and all notifications suppressed, but the individual toggle states shall be preserved.
- Status: Planned
- fulfills -> FEAT-009

## REQ-461: FR-M10-003 (Requirement)
The sheet shall display individual on/off toggles for the following notification categories: Watering Reminders, Feeding Reminders, Pest and Disease Alerts, Weather-Based Care Updates, Community Activity (Clusters and Challenges), and Weekly Bloom Report. Each toggle shall have an icon and a one-line description.
- Status: Planned
- fulfills -> FEAT-009

## REQ-462: FR-M10-004 (Requirement)
Toggling any individual category shall take immediate effect without requiring a "Save" action.
- Status: Planned
- fulfills -> FEAT-009

## REQ-463: FR-M10-005 (Requirement)
The sheet shall display a timing preference section with a radio selector: Morning (7–9 AM), Afternoon (12–2 PM), Evening (6–8 PM). The selected preference shall apply to all new care reminder notifications.
- Status: Planned
- fulfills -> FEAT-009

## REQ-464: FR-M10-006 (Requirement)
The sheet shall display a "Skip weekends" toggle. When enabled, no care reminders shall fire on Saturdays or Sundays.
- Status: Planned
- fulfills -> FEAT-009

## REQ-465: FR-M10-007 (Requirement)
The sheet shall display a "Travel Mode" toggle. When enabled, a date range picker shall appear to set the start and end dates of travel. All notifications shall be suppressed during the travel period. The schedule data shall remain intact.
- Status: Planned
- fulfills -> FEAT-009

## REQ-466: FR-M10-008 (Requirement)
The sheet shall display a "Save Preferences" primary button. Tapping it shall persist all toggle states and dismiss the sheet.
- Status: Planned
- fulfills -> FEAT-009

## REQ-467: FR-M10-009 (Requirement)
A "Cancel" text link shall dismiss the sheet without saving any changes made during the current session.
- Status: Planned
- fulfills -> FEAT-009

## REQ-468: FR-M11-001 (Requirement)
The Weekly Bloom Report Sheet shall be triggered by: the "View Report" button on the Weekly Bloom Report banner on SCR-01 Dashboard, and by tapping a "Weekly Bloom Report" push notification.
- Status: Planned
- fulfills -> FEAT-020

## REQ-469: FR-M11-002 (Requirement)
The system shall surface the Weekly Bloom Report banner on SCR-01 Dashboard on Monday mornings, or on the first app open after a lapse where the user has at least 7 days of log data.
- Status: Planned
- fulfills -> FEAT-020

## REQ-470: FR-M11-003 (Requirement)
The sheet shall display a date range label covering the previous week (e.g., "May 26 – Jun 1, 2026").
- Status: Planned
- fulfills -> FEAT-020

## REQ-471: FR-M11-004 (Requirement)
The sheet shall display a summary stats row with four pill cards: plants logged count for the week, total log entries for the week, Garden Health Score change from the previous week (e.g., "+7 pts" or "−2 pts"), and current streak status.
- Status: Planned
- fulfills -> FEAT-020

## REQ-472: FR-M11-005 (Requirement)
The sheet shall display a "Best performing plant this week" spotlight card showing: plant thumbnail, plant name, growing method badge, and the most notable health improvement for that plant.
- Status: Planned
- fulfills -> FEAT-020

## REQ-473: FR-M11-006 (Requirement)
The sheet shall display a weather correlation insight derived from the week's weather data and log entries (e.g., "Your tomatoes logged their best growth rate on the 3 sunniest days this week").
- Status: Planned
- fulfills -> FEAT-020

## REQ-474: FR-M11-007 (Requirement)
When the user archived at least one plant during the week, the sheet shall display a conditional alert row: "⚠ [N] plant(s) archived this week → See Cemetery Log" with a tappable link to SCR-14.
- Status: Planned
- fulfills -> FEAT-020

## REQ-475: FR-M11-008 (Requirement)
The sheet shall display a "Next week tip" card containing a contextual tip based on the upcoming week's forecast for the user's zone (e.g., "Frost risk on Friday → bring indoor plants in by Thursday"). This tip shall come from the Smart Tips Library, not auto-generated text.
- Status: Planned
- fulfills -> FEAT-020

## REQ-476: FR-M11-009 (Requirement)
The sheet shall provide a "Share Report" icon button that opens MOD-12 Export / Share Sheet with a summary image of the weekly report as the shareable content.
- Status: Planned
- fulfills -> FEAT-020

## REQ-477: FR-M11-010 (Requirement)
The sheet shall provide a "View Full Garden →" CTA button that dismisses the sheet and navigates to SCR-02 Plant List.
- Status: Planned
- fulfills -> FEAT-020

## REQ-478: FR-M11-011 (Requirement)
A "Dismiss" text link at the bottom shall close the sheet without any navigation action.
- Status: Planned
- fulfills -> FEAT-020

## REQ-479: FR-M12-001 (Requirement)
The Export / Share Sheet shall be triggered by: the Share action pill on SCR-03 Plant Detail, the Export / Share button on SCR-05 Calculator results (after MOD-05 completes), the Share icon on SCR-09 Garden Cluster Detail, the Share button on SCR-11 Profile badge detail, the Share / Download actions on SCR-15 Reels Gallery (after MOD-05 completes), the Share button in MOD-09 Tip Article Reader, and the Share Report button in MOD-11 Weekly Bloom Report.
- Status: Planned
- fulfills -> FEAT-031

## REQ-480: FR-M12-002 (Requirement)
Before the native OS share sheet is presented, the system shall display a GardenPulse pre-share layer showing a content preview (photo thumbnail, PDF preview, or reel frame), and format options relevant to the current content type.
- Status: Planned
- fulfills -> FEAT-031

## REQ-481: FR-M12-003 (Requirement)
Format options shall be displayed contextually based on what is being shared:
- Status: Planned
- fulfills -> FEAT-031

## REQ-482: FR-M12-004 (Requirement)
The pre-share layer shall display a "Copy Text Summary" option where applicable, copying a plain-text version of the content to the device clipboard.
- Status: Planned
- fulfills -> FEAT-031

## REQ-483: FR-M12-005 (Requirement)
All image and video exports shall include the GardenPulse watermark by default.
- Status: Planned
- fulfills -> FEAT-031

## REQ-484: FR-M12-006 (Requirement)
Users who have purchased the Supporter Badge shall see a "Include GardenPulse branding" toggle on the pre-share layer. Disabling this toggle shall remove the watermark from the exported content.
- Status: Planned
- fulfills -> FEAT-031

## REQ-485: FR-M12-007 (Requirement)
Users who have NOT purchased the Supporter Badge shall not see the watermark toggle; the watermark shall be applied without option to remove.
- Status: Planned
- fulfills -> FEAT-031

## REQ-486: FR-M12-008 (Requirement)
Tapping "Continue to Share →" on the pre-share layer shall open the native platform share sheet (iOS Share Sheet / Android Share Intent) with the selected content ready.
- Status: Planned
- fulfills -> FEAT-031

## REQ-487: FR-M12-009 (Requirement)
The native OS share sheet shall display standard platform sharing destinations (Instagram, TikTok, WhatsApp, Messages, Copy Link, Save to Photos, and others as provided by the OS).
- Status: Planned
- fulfills -> FEAT-031

## REQ-488: FR-M12-010 (Requirement)
A "Cancel" button shall be available on the pre-share layer to dismiss without proceeding to the OS share sheet.
- Status: Planned
- fulfills -> FEAT-031

## SCR-001: ONB-1 - Splash Screen (Screen)
Standardized app layout and flow for Splash Screen (Onboarding).
- Status: In Progress
- implements -> REQ-025
- implements -> REQ-026
- implements -> REQ-027
- implements -> REQ-028
- implements -> REQ-029
- implements -> REQ-030
- implements -> REQ-031
- implements -> REQ-001

## SCR-002: ONB-2 - Welcome + Method Selection (Screen)
Standardized app layout and flow for Welcome + Method Selection (Onboarding).
- Status: In Progress
- implements -> REQ-032
- implements -> REQ-033
- implements -> REQ-034
- implements -> REQ-035
- implements -> REQ-036
- implements -> REQ-037
- implements -> REQ-038
- implements -> REQ-039
- implements -> REQ-040
- implements -> REQ-041
- implements -> REQ-004
- implements -> REQ-005
- implements -> REQ-006

## SCR-003: ONB-3 - Add First Plant (Screen)
Standardized app layout and flow for Add First Plant (Onboarding).
- Status: In Progress
- implements -> REQ-042
- implements -> REQ-043
- implements -> REQ-044
- implements -> REQ-045
- implements -> REQ-046
- implements -> REQ-047
- implements -> REQ-048
- implements -> REQ-049
- implements -> REQ-050
- implements -> REQ-051
- implements -> REQ-052
- implements -> REQ-053
- implements -> REQ-054
- implements -> REQ-055

## SCR-004: ONB-4 - Instant Care Plan Preview (Screen)
Standardized app layout and flow for Instant Care Plan Preview (Onboarding).
- Status: In Progress
- implements -> REQ-056
- implements -> REQ-057
- implements -> REQ-058
- implements -> REQ-059
- implements -> REQ-060
- implements -> REQ-061
- implements -> REQ-062
- implements -> REQ-063
- implements -> REQ-064
- implements -> REQ-065
- implements -> REQ-066
- implements -> REQ-067

## SCR-005: SCR-01 - Dashboard / Home (Screen)
Standardized app layout and flow for Dashboard / Home (Screen).
- Status: In Progress
- implements -> REQ-068
- implements -> REQ-069
- implements -> REQ-070
- implements -> REQ-071
- implements -> REQ-072
- implements -> REQ-073
- implements -> REQ-074
- implements -> REQ-075
- implements -> REQ-076
- implements -> REQ-077
- implements -> REQ-078
- implements -> REQ-079
- implements -> REQ-080
- implements -> REQ-081
- implements -> REQ-082
- implements -> REQ-083
- implements -> REQ-084
- implements -> REQ-085
- implements -> REQ-086
- implements -> REQ-087
- implements -> REQ-088
- implements -> REQ-089
- implements -> REQ-090
- implements -> REQ-091
- implements -> REQ-092
- implements -> REQ-093
- implements -> REQ-094
- implements -> REQ-095
- implements -> REQ-096
- implements -> REQ-097
- implements -> REQ-098
- implements -> REQ-001
- implements -> REQ-002
- implements -> REQ-003
- implements -> REQ-007
- implements -> REQ-008
- implements -> REQ-009
- implements -> REQ-010
- implements -> REQ-011
- implements -> REQ-012
- implements -> REQ-013

## SCR-006: SCR-02 - Plant List (Screen)
Standardized app layout and flow for Plant List (Screen).
- Status: In Progress
- implements -> REQ-099
- implements -> REQ-100
- implements -> REQ-101
- implements -> REQ-102
- implements -> REQ-103
- implements -> REQ-104
- implements -> REQ-105
- implements -> REQ-106
- implements -> REQ-107
- implements -> REQ-108
- implements -> REQ-109
- implements -> REQ-110
- implements -> REQ-111
- implements -> REQ-112
- implements -> REQ-113
- implements -> REQ-114
- implements -> REQ-115
- implements -> REQ-116

## SCR-007: SCR-03 - Plant Detail (Screen)
Standardized app layout and flow for Plant Detail (Screen).
- Status: In Progress
- implements -> REQ-117
- implements -> REQ-118
- implements -> REQ-119
- implements -> REQ-120
- implements -> REQ-121
- implements -> REQ-122
- implements -> REQ-123
- implements -> REQ-124
- implements -> REQ-125
- implements -> REQ-126
- implements -> REQ-127
- implements -> REQ-128
- implements -> REQ-129
- implements -> REQ-130
- implements -> REQ-131
- implements -> REQ-132
- implements -> REQ-133
- implements -> REQ-134
- implements -> REQ-135
- implements -> REQ-136
- implements -> REQ-137
- implements -> REQ-138
- implements -> REQ-139
- implements -> REQ-140
- implements -> REQ-141
- implements -> REQ-142
- implements -> REQ-143
- implements -> REQ-144
- implements -> REQ-145
- implements -> REQ-146
- implements -> REQ-147

## SCR-008: SCR-15 - Progress Reels Gallery (Screen)
Standardized app layout and flow for Progress Reels Gallery (Screen).
- Status: In Progress
- implements -> REQ-148
- implements -> REQ-149
- implements -> REQ-150
- implements -> REQ-151
- implements -> REQ-152
- implements -> REQ-153
- implements -> REQ-154
- implements -> REQ-155
- implements -> REQ-156
- implements -> REQ-157
- implements -> REQ-158
- implements -> REQ-159
- implements -> REQ-160

## SCR-009: SCR-04 - Tools Hub (Screen)
Standardized app layout and flow for Tools Hub (Screen).
- Status: In Progress
- implements -> REQ-161
- implements -> REQ-162
- implements -> REQ-163
- implements -> REQ-164
- implements -> REQ-165
- implements -> REQ-166
- implements -> REQ-167
- implements -> REQ-168
- implements -> REQ-169

## SCR-010: SCR-05 - Nutrient / Recipe Calculator (Screen)
Standardized app layout and flow for Nutrient / Recipe Calculator (Screen).
- Status: In Progress
- implements -> REQ-170
- implements -> REQ-171
- implements -> REQ-172
- implements -> REQ-173
- implements -> REQ-174
- implements -> REQ-175
- implements -> REQ-176
- implements -> REQ-177
- implements -> REQ-178
- implements -> REQ-179
- implements -> REQ-180
- implements -> REQ-181
- implements -> REQ-182
- implements -> REQ-183
- implements -> REQ-184
- implements -> REQ-185
- implements -> REQ-186
- implements -> REQ-187
- implements -> REQ-188
- implements -> REQ-189
- implements -> REQ-190

## SCR-011: SCR-06 - Leaf Diagnostics (Screen)
Standardized app layout and flow for Leaf Diagnostics (Screen).
- Status: In Progress
- implements -> REQ-191
- implements -> REQ-192
- implements -> REQ-193
- implements -> REQ-194
- implements -> REQ-195
- implements -> REQ-196
- implements -> REQ-197
- implements -> REQ-198
- implements -> REQ-199
- implements -> REQ-200
- implements -> REQ-201
- implements -> REQ-202
- implements -> REQ-203
- implements -> REQ-204
- implements -> REQ-205
- implements -> REQ-206
- implements -> REQ-207
- implements -> REQ-208
- implements -> REQ-209
- implements -> REQ-210
- implements -> REQ-211

## SCR-012: SCR-07 - Smart Scheduler (Screen)
Standardized app layout and flow for Smart Scheduler (Screen).
- Status: In Progress
- implements -> REQ-212
- implements -> REQ-213
- implements -> REQ-214
- implements -> REQ-215
- implements -> REQ-216
- implements -> REQ-217
- implements -> REQ-218
- implements -> REQ-219
- implements -> REQ-220
- implements -> REQ-221
- implements -> REQ-222
- implements -> REQ-223
- implements -> REQ-224
- implements -> REQ-225
- implements -> REQ-226
- implements -> REQ-227
- implements -> REQ-228
- implements -> REQ-229
- implements -> REQ-230
- implements -> REQ-231

## SCR-013: SCR-08 - Community Hub (Screen)
Standardized app layout and flow for Community Hub (Screen).
- Status: In Progress
- implements -> REQ-232
- implements -> REQ-233
- implements -> REQ-234
- implements -> REQ-235
- implements -> REQ-236
- implements -> REQ-237
- implements -> REQ-238
- implements -> REQ-239
- implements -> REQ-240
- implements -> REQ-241
- implements -> REQ-242
- implements -> REQ-243
- implements -> REQ-244
- implements -> REQ-245
- implements -> REQ-246
- implements -> REQ-247
- implements -> REQ-248

## SCR-014: SCR-09 - Garden Cluster Detail (Screen)
Standardized app layout and flow for Garden Cluster Detail (Screen).
- Status: In Progress
- implements -> REQ-249
- implements -> REQ-250
- implements -> REQ-251
- implements -> REQ-252
- implements -> REQ-253
- implements -> REQ-254
- implements -> REQ-255
- implements -> REQ-256
- implements -> REQ-257
- implements -> REQ-258
- implements -> REQ-259
- implements -> REQ-260
- implements -> REQ-261
- implements -> REQ-262

## SCR-015: SCR-10 - Local Grow Map (Screen)
Standardized app layout and flow for Local Grow Map (Screen).
- Status: In Progress
- implements -> REQ-263
- implements -> REQ-264
- implements -> REQ-265
- implements -> REQ-266
- implements -> REQ-267
- implements -> REQ-268
- implements -> REQ-269
- implements -> REQ-270
- implements -> REQ-271
- implements -> REQ-272
- implements -> REQ-273
- implements -> REQ-274
- implements -> REQ-275
- implements -> REQ-276
- implements -> REQ-010

## SCR-016: SCR-11 - Profile & Badges (Screen)
Standardized app layout and flow for Profile & Badges (Screen).
- Status: In Progress
- implements -> REQ-277
- implements -> REQ-278
- implements -> REQ-279
- implements -> REQ-280
- implements -> REQ-281
- implements -> REQ-282
- implements -> REQ-283
- implements -> REQ-284
- implements -> REQ-285
- implements -> REQ-286
- implements -> REQ-287
- implements -> REQ-288
- implements -> REQ-289
- implements -> REQ-290
- implements -> REQ-291
- implements -> REQ-292
- implements -> REQ-293
- implements -> REQ-294
- implements -> REQ-295

## SCR-017: SCR-12 - Settings (Screen)
Standardized app layout and flow for Settings (Screen).
- Status: In Progress
- implements -> REQ-296
- implements -> REQ-297
- implements -> REQ-298
- implements -> REQ-299
- implements -> REQ-300
- implements -> REQ-301
- implements -> REQ-302
- implements -> REQ-303
- implements -> REQ-304
- implements -> REQ-305
- implements -> REQ-306
- implements -> REQ-307
- implements -> REQ-308
- implements -> REQ-309
- implements -> REQ-310
- implements -> REQ-311
- implements -> REQ-312
- implements -> REQ-313
- implements -> REQ-314
- implements -> REQ-315
- implements -> REQ-316
- implements -> REQ-317
- implements -> REQ-318
- implements -> REQ-319
- implements -> REQ-320
- implements -> REQ-022
- implements -> REQ-023
- implements -> REQ-024

## SCR-018: SCR-13 - Privacy Dashboard (Screen)
Standardized app layout and flow for Privacy Dashboard (Screen).
- Status: In Progress
- implements -> REQ-321
- implements -> REQ-322
- implements -> REQ-323
- implements -> REQ-324
- implements -> REQ-325
- implements -> REQ-326
- implements -> REQ-327
- implements -> REQ-328
- implements -> REQ-329
- implements -> REQ-330
- implements -> REQ-331
- implements -> REQ-332
- implements -> REQ-333
- implements -> REQ-018
- implements -> REQ-019
- implements -> REQ-020
- implements -> REQ-021

## SCR-019: SCR-14 - Cemetery Log (Screen)
Standardized app layout and flow for Cemetery Log (Screen).
- Status: In Progress
- implements -> REQ-334
- implements -> REQ-335
- implements -> REQ-336
- implements -> REQ-337
- implements -> REQ-338
- implements -> REQ-339
- implements -> REQ-340
- implements -> REQ-341
- implements -> REQ-342
- implements -> REQ-343
- implements -> REQ-344
- implements -> REQ-345
- implements -> REQ-346

## SCR-020: SCR-16 - Creator Studio (Screen)
Standardized app layout and flow for Creator Studio (Screen).
- Status: In Progress
- implements -> REQ-347
- implements -> REQ-348
- implements -> REQ-349
- implements -> REQ-350
- implements -> REQ-351
- implements -> REQ-352
- implements -> REQ-353
- implements -> REQ-354
- implements -> REQ-355
- implements -> REQ-356
- implements -> REQ-357
- implements -> REQ-358
- implements -> REQ-359
- implements -> REQ-360
- implements -> REQ-361
- implements -> REQ-362
- implements -> REQ-363

## SCR-021: MOD-01 - Quick Log Sheet (Screen)
Standardized app layout and flow for Quick Log Sheet (Modal).
- Status: In Progress
- implements -> REQ-364
- implements -> REQ-365
- implements -> REQ-366
- implements -> REQ-367
- implements -> REQ-368
- implements -> REQ-369
- implements -> REQ-370
- implements -> REQ-371
- implements -> REQ-372
- implements -> REQ-373
- implements -> REQ-374
- implements -> REQ-375
- implements -> REQ-376
- implements -> REQ-377
- implements -> REQ-378

## SCR-022: MOD-02 - Add / Edit Plant Sheet (Screen)
Standardized app layout and flow for Add / Edit Plant Sheet (Modal).
- Status: In Progress
- implements -> REQ-379
- implements -> REQ-380
- implements -> REQ-381
- implements -> REQ-382
- implements -> REQ-383
- implements -> REQ-384
- implements -> REQ-385
- implements -> REQ-386
- implements -> REQ-387
- implements -> REQ-388
- implements -> REQ-389
- implements -> REQ-390
- implements -> REQ-391
- implements -> REQ-392
- implements -> REQ-393

## SCR-023: MOD-03 - QR Scanner Overlay (Screen)
Standardized app layout and flow for QR Scanner Overlay (Modal).
- Status: In Progress
- implements -> REQ-394
- implements -> REQ-395
- implements -> REQ-396
- implements -> REQ-397
- implements -> REQ-398
- implements -> REQ-399
- implements -> REQ-400
- implements -> REQ-401
- implements -> REQ-402
- implements -> REQ-403
- implements -> REQ-404

## SCR-024: MOD-04 - Permission Context Modal (Screen)
Standardized app layout and flow for Permission Context Modal (Modal).
- Status: In Progress
- implements -> REQ-405
- implements -> REQ-406
- implements -> REQ-407
- implements -> REQ-408
- implements -> REQ-409
- implements -> REQ-410
- implements -> REQ-411
- implements -> REQ-412
- implements -> REQ-413
- implements -> REQ-414
- implements -> REQ-415
- implements -> REQ-416
- implements -> REQ-018
- implements -> REQ-019
- implements -> REQ-020
- implements -> REQ-021

## SCR-025: MOD-05 - Rewarded Video Prompt (Screen)
Standardized app layout and flow for Rewarded Video Prompt (Modal).
- Status: In Progress
- implements -> REQ-417
- implements -> REQ-418
- implements -> REQ-419
- implements -> REQ-420
- implements -> REQ-421
- implements -> REQ-422
- implements -> REQ-423
- implements -> REQ-424
- implements -> REQ-425
- implements -> REQ-014
- implements -> REQ-015
- implements -> REQ-016
- implements -> REQ-017

## SCR-026: MOD-06 - Interstitial Ad (Screen)
Standardized app layout and flow for Interstitial Ad (Modal).
- Status: In Progress
- implements -> REQ-426
- implements -> REQ-427
- implements -> REQ-428
- implements -> REQ-429
- implements -> REQ-430
- implements -> REQ-014
- implements -> REQ-015
- implements -> REQ-016
- implements -> REQ-017

## SCR-027: MOD-07 - Supporter Badge Dialog (Screen)
Standardized app layout and flow for Supporter Badge Dialog (Modal).
- Status: In Progress
- implements -> REQ-431
- implements -> REQ-432
- implements -> REQ-433
- implements -> REQ-434
- implements -> REQ-435
- implements -> REQ-436
- implements -> REQ-437
- implements -> REQ-438
- implements -> REQ-014
- implements -> REQ-015
- implements -> REQ-016
- implements -> REQ-017

## SCR-028: MOD-08 - Batch Mode Overlay (Screen)
Standardized app layout and flow for Batch Mode Overlay (Modal).
- Status: In Progress
- implements -> REQ-439
- implements -> REQ-440
- implements -> REQ-441
- implements -> REQ-442
- implements -> REQ-443
- implements -> REQ-444
- implements -> REQ-445
- implements -> REQ-446
- implements -> REQ-447
- implements -> REQ-448

## SCR-029: MOD-09 - Tip Article Reader Sheet (Screen)
Standardized app layout and flow for Tip Article Reader Sheet (Modal).
- Status: In Progress
- implements -> REQ-449
- implements -> REQ-450
- implements -> REQ-451
- implements -> REQ-452
- implements -> REQ-453
- implements -> REQ-454
- implements -> REQ-455
- implements -> REQ-456
- implements -> REQ-457
- implements -> REQ-458

## SCR-030: MOD-10 - Notification Preferences Sheet (Screen)
Standardized app layout and flow for Notification Preferences Sheet (Modal).
- Status: In Progress
- implements -> REQ-459
- implements -> REQ-460
- implements -> REQ-461
- implements -> REQ-462
- implements -> REQ-463
- implements -> REQ-464
- implements -> REQ-465
- implements -> REQ-466
- implements -> REQ-467

## SCR-031: MOD-11 - Weekly Bloom Report Sheet (Screen)
Standardized app layout and flow for Weekly Bloom Report Sheet (Modal).
- Status: In Progress
- implements -> REQ-468
- implements -> REQ-469
- implements -> REQ-470
- implements -> REQ-471
- implements -> REQ-472
- implements -> REQ-473
- implements -> REQ-474
- implements -> REQ-475
- implements -> REQ-476
- implements -> REQ-477
- implements -> REQ-478

## SCR-032: MOD-12 - Export / Share Sheet (Screen)
Standardized app layout and flow for Export / Share Sheet (Modal).
- Status: In Progress
- implements -> REQ-479
- implements -> REQ-480
- implements -> REQ-481
- implements -> REQ-482
- implements -> REQ-483
- implements -> REQ-484
- implements -> REQ-485
- implements -> REQ-486
- implements -> REQ-487
- implements -> REQ-488

## UI-GLB-BACK-BTN: Global Back Button (UI-Element)
Reusable navigation button to return to the previous screen.
- Status: In Progress
- parent -> SCR-003
- parent -> SCR-004
- parent -> SCR-007
- parent -> SCR-008
- parent -> SCR-010
- parent -> SCR-011
- parent -> SCR-011
- parent -> SCR-012
- parent -> SCR-014
- parent -> SCR-015
- parent -> SCR-017
- parent -> SCR-017
- parent -> SCR-018
- parent -> SCR-019
- parent -> SCR-020
- parent -> SCR-024

## UI-GLB-SETTINGS-ICON: Global Settings Icon (UI-Element)
Reusable icon linking to settings.
- Status: In Progress
- parent -> SCR-005
- parent -> SCR-011
- parent -> SCR-016
- parent -> SCR-024

## UI-GLB-BELL-ICON: Global Notification Bell (UI-Element)
Reusable icon showing unread notification badge.
- Status: In Progress
- parent -> SCR-004
- parent -> SCR-005

## UI-GLB-CLOSE-BTN: Global Close Button (UI-Element)
Reusable close or dismiss icon button.
- Status: In Progress
- parent -> SCR-023
- parent -> SCR-026
- parent -> SCR-029
- parent -> SCR-031

## UI-GLB-BOTTOM-NAV: Global Bottom Navigation (UI-Element)
Universal 5-tab application navigation bar.
- Status: In Progress
- parent -> SCR-005
- parent -> SCR-005
- parent -> SCR-006
- parent -> SCR-006
- parent -> SCR-007
- parent -> SCR-007
- parent -> SCR-009
- parent -> SCR-009
- parent -> SCR-010
- parent -> SCR-010
- parent -> SCR-011
- parent -> SCR-011
- parent -> SCR-012
- parent -> SCR-012
- parent -> SCR-013
- parent -> SCR-013
- parent -> SCR-014
- parent -> SCR-014

## UI-GLB-FAB: Global Floating Action Button (UI-Element)
Universal floating action button for quick actions.
- Status: In Progress
- parent -> SCR-005
- parent -> SCR-005
- parent -> SCR-006
- parent -> SCR-006
- parent -> SCR-007
- parent -> SCR-007
- parent -> SCR-014
- parent -> SCR-014
- parent -> SCR-021

## UI-GLB-SEARCH-BAR: Global Search Bar (UI-Element)
Reusable input field with search icon for filtering lists.
- Status: In Progress
- parent -> SCR-003
- parent -> SCR-006
- parent -> SCR-022

## UI-GLB-PRIMARY-CTA: Global Primary CTA Button (UI-Element)
Standard full-width green action button.
- Status: In Progress
- parent -> SCR-002
- parent -> SCR-002
- parent -> SCR-003
- parent -> SCR-004
- parent -> SCR-010
- parent -> SCR-020
- parent -> SCR-024
- parent -> SCR-025
- parent -> SCR-027
- parent -> SCR-030

## UI-GLB-SECONDARY-LINK: Global Secondary Text Link (UI-Element)
Standard text-only low-emphasis action link.
- Status: In Progress
- parent -> SCR-002
- parent -> SCR-002
- parent -> SCR-003
- parent -> SCR-004
- parent -> SCR-025

## UI-GLB-MIC-ICON: Global Voice Input Icon (UI-Element)
Reusable mic icon for hands-free voice transcription.
- Status: In Progress
- parent -> SCR-007
- parent -> SCR-017
- parent -> SCR-024
- parent -> SCR-024
- parent -> SCR-024

## UI-GLB-CAMERA-BTN: Global Camera Scan Button (UI-Element)
Reusable button for triggering device camera capture.
- Status: In Progress
- parent -> SCR-003
- parent -> SCR-003
- parent -> SCR-011
- parent -> SCR-022
- parent -> SCR-024
- parent -> SCR-024

## UI-GLB-NATIVE-AD: Global Native Ad Card (UI-Element)
Standard in-feed card styled as regular content for AdMob.
- Status: In Progress
- parent -> SCR-006
- parent -> SCR-009
- parent -> SCR-013
- parent -> SCR-020
- parent -> SCR-027
- parent -> SCR-029

## UI-GLB-DATE-PICKER: Global Date Picker (UI-Element)
Standard platform date picker widget.
- Status: In Progress
- parent -> SCR-003
- parent -> SCR-012
- parent -> SCR-022
- parent -> SCR-022

## UI-GLB-LOCATION-BADGE: Global Location/Zone Badge (UI-Element)
Standard badge displaying detected city and planting zone.
- Status: In Progress
- parent -> SCR-003
- parent -> SCR-004
- parent -> SCR-005
- parent -> SCR-021

## UI-GLB-LOADING-SPINNER: Global Loading Spinner (UI-Element)
Standard loading indicator for async actions.
- Status: In Progress
- parent -> SCR-001

## UI-GLB-SAVE-BTN: Global Save/Commit Button (UI-Element)
Standard button to save data and submit forms.
- Status: In Progress
- parent -> SCR-010
- parent -> SCR-014
- parent -> SCR-021
- parent -> SCR-022

## UI-GLB-TOGGLE: Global Toggle Switch (UI-Element)
Standard on/off toggle or multi-select checkbox.
- Status: In Progress
- parent -> SCR-004
- parent -> SCR-006
- parent -> SCR-006
- parent -> SCR-006
- parent -> SCR-007
- parent -> SCR-008
- parent -> SCR-010
- parent -> SCR-011
- parent -> SCR-012
- parent -> SCR-012
- parent -> SCR-012
- parent -> SCR-012
- parent -> SCR-012
- parent -> SCR-014
- parent -> SCR-015
- parent -> SCR-015
- parent -> SCR-015
- parent -> SCR-017
- parent -> SCR-017
- parent -> SCR-017
- parent -> SCR-017
- parent -> SCR-017
- parent -> SCR-017
- parent -> SCR-017
- parent -> SCR-017
- parent -> SCR-017
- parent -> SCR-017
- parent -> SCR-018
- parent -> SCR-018
- parent -> SCR-018
- parent -> SCR-020
- parent -> SCR-021
- parent -> SCR-022
- parent -> SCR-023
- parent -> SCR-024
- parent -> SCR-028
- parent -> SCR-030
- parent -> SCR-030
- parent -> SCR-030
- parent -> SCR-030
- parent -> SCR-032

## UI-001: *Access:** App first launch (UI-Element)
- Status: In Progress
- parent -> SCR-001

## UI-002: *Purpose:** Brand entry, initialization (UI-Element)
- Status: In Progress
- parent -> SCR-001

## UI-003: *Elements** (UI-Element)
- Status: In Progress
- parent -> SCR-001

## UI-004: App logo (UI-Element)
animated leaf unfurl
- Status: In Progress
- parent -> SCR-001

## UI-005: App name "GardenPulse" wordmark (UI-Element)
- Status: In Progress
- parent -> SCR-001

## UI-006: Tagline label: "Grow Smarter, Anywhere." (UI-Element)
- Status: In Progress
- parent -> SCR-001

## UI-007: -- (UI-Element)
- Status: In Progress
- parent -> SCR-001

## UI-008: *Access:** After ONB-1 (UI-Element)
- Status: In Progress
- parent -> SCR-002

## UI-009: *Purpose:** Establish growing method so the entire app adapts (UI-Element)
Step 1 of 3
- Status: In Progress
- parent -> SCR-002

## UI-010: *Header** (UI-Element)
- Status: In Progress
- parent -> SCR-002

## UI-011: Progress indicator (UI-Element)
Step 1 of 3
- Status: In Progress
- parent -> SCR-002

## UI-012: *Main Content** (UI-Element)
- Status: In Progress
- parent -> SCR-002

## UI-013: Heading: "How do you grow?" (UI-Element)
- Status: In Progress
- parent -> SCR-002

## UI-014: Sub-label: "Pick your primary method — you can mix later" (UI-Element)
- Status: In Progress
- parent -> SCR-002

## UI-015: 4 selectable method cards (single-select, tap to highlight): (UI-Element)
- Status: In Progress
- parent -> SCR-002

## UI-016: Soil / Raised Bed (UI-Element)
icon + name + one-line description
- Status: In Progress
- parent -> SCR-002

## UI-017: Container / Balcony (UI-Element)
icon + name + one-line description
- Status: In Progress
- parent -> SCR-002

## UI-018: Hydroponic (UI-Element)
icon + name + one-line description
- Status: In Progress
- parent -> SCR-002

## UI-019: Indoor Plants (UI-Element)
icon + name + one-line description
- Status: In Progress
- parent -> SCR-002

## UI-020: Each card: icon, method name, brief description, selection ring on tap (UI-Element)
- Status: In Progress
- parent -> SCR-002

## UI-021: *Actions** (UI-Element)
- Status: In Progress
- parent -> SCR-002

## UI-022: *Modal Triggered** (UI-Element)
- Status: In Progress
- parent -> SCR-002

## UI-023: -- (UI-Element)
- Status: In Progress
- parent -> SCR-002

## UI-024: *Access:** After ONB-2 (UI-Element)
and after location permission prompt in MOD-04
- Status: In Progress
- parent -> SCR-003

## UI-025: *Purpose:** Capture first plant to immediately personalize the app (UI-Element)
Step 2 of 3
- Status: In Progress
- parent -> SCR-003

## UI-026: *Header** (UI-Element)
- Status: In Progress
- parent -> SCR-003

## UI-027: Progress indicator (UI-Element)
Step 2 of 3
- Status: In Progress
- parent -> SCR-003

## UI-028: *Main Content** (UI-Element)
- Status: In Progress
- parent -> SCR-003

## UI-029: Heading: "Add your first plant" (UI-Element)
- Status: In Progress
- parent -> SCR-003

## UI-030: OR divider (UI-Element)
- Status: In Progress
- parent -> SCR-003

## UI-031: Browse by category: grid of plant type chips (UI-Element)
Herb · Vegetable · Fruit · Flower · Houseplant · Microgreen
- Status: In Progress
- parent -> SCR-003

## UI-032: Selected plant preview card: photo thumbnail, common name, scientific name, method compatibility badge (UI-Element)
- Status: In Progress
- parent -> SCR-003

## UI-033: Plant nickname field (UI-Element)
optional, character limit 30
- Status: In Progress
- parent -> SCR-003

## UI-034: Growing method selector pills (pre-filled from ONB-2, editable): Soil · Container · Hydro · Indoor (UI-Element)
- Status: In Progress
- parent -> SCR-003

## UI-035: *Actions** (UI-Element)
- Status: In Progress
- parent -> SCR-003

## UI-036: -- (UI-Element)
- Status: In Progress
- parent -> SCR-003

## UI-037: *Access:** After ONB-3 (UI-Element)
- Status: In Progress
- parent -> SCR-004

## UI-038: *Purpose:** Show immediate value — user sees their personalised plan before entering the main app (UI-Element)
Step 3 of 3
- Status: In Progress
- parent -> SCR-004

## UI-039: *Header** (UI-Element)
- Status: In Progress
- parent -> SCR-004

## UI-040: Progress indicator (UI-Element)
Step 3 of 3
- Status: In Progress
- parent -> SCR-004

## UI-041: *Main Content** (UI-Element)
- Status: In Progress
- parent -> SCR-004

## UI-042: Success heading: "Your care plan is ready!" (UI-Element)
- Status: In Progress
- parent -> SCR-004

## UI-043: First plant care summary card: (UI-Element)
- Status: In Progress
- parent -> SCR-004

## UI-044: Watering frequency label (UI-Element)
e.g., "Every 2 days"
- Status: In Progress
- parent -> SCR-004

## UI-045: Light requirement badge (UI-Element)
e.g., "Bright indirect"
- Status: In Progress
- parent -> SCR-004

## UI-046: Next action chip (UI-Element)
e.g., "Water today"
- Status: In Progress
- parent -> SCR-004

## UI-047: Growing method tag (UI-Element)
- Status: In Progress
- parent -> SCR-004

## UI-048: Garden Health Score™ baseline card: circular score (initial 50/100), label "We'll track your progress from here" (UI-Element)
- Status: In Progress
- parent -> SCR-004

## UI-049: *Actions** (UI-Element)
- Status: In Progress
- parent -> SCR-004

## UI-050: *Modal Triggered** (UI-Element)
- Status: In Progress
- parent -> SCR-004

## UI-051: -- (UI-Element)
- Status: In Progress
- parent -> SCR-004

## UI-052: -- (UI-Element)
- Status: In Progress
- parent -> SCR-004

## UI-053: *Tab:** Home (UI-Element)
Tab 1
- Status: In Progress
- parent -> SCR-005

## UI-054: *Purpose:** Daily hub — tasks, weather, garden health at a glance, quick logging entry point (UI-Element)
- Status: In Progress
- parent -> SCR-005

## UI-055: *Header / AppBar** (UI-Element)
- Status: In Progress
- parent -> SCR-005

## UI-056: GardenPulse logo (UI-Element)
left
- Status: In Progress
- parent -> SCR-005

## UI-057: *Main Content (scrollable feed)** (UI-Element)
- Status: In Progress
- parent -> SCR-005

## UI-058: Current temperature, humidity %, UV index, rain chance (UI-Element)
- Status: In Progress
- parent -> SCR-005

## UI-059: Forecast strip: next 3 days (UI-Element)
icon + high/low temp
- Status: In Progress
- parent -> SCR-005

## UI-060: Smart alert label (UI-Element)
conditional, e.g., "Rain tomorrow → skip watering today"
- Status: In Progress
- parent -> SCR-005

## UI-061: Pull-to-refresh zone (UI-Element)
refreshes weather from OpenWeatherMap; uses cached 7-day forecast between refreshes to reduce API calls
- Status: In Progress
- parent -> SCR-005

## UI-062: Animated welcome-back illustration (UI-Element)
- Status: In Progress
- parent -> SCR-005

## UI-063: "Welcome back! Your [plant name] missed you 🌱" label (UI-Element)
- Status: In Progress
- parent -> SCR-005

## UI-064: See What Needs Attention → button → SCR-02 Plant List, sorted by last-logged date (UI-Element)
`See What Needs Attention →` button → SCR-02 Plant List, sorted by last-logged date
- Status: In Progress
- parent -> SCR-005

## UI-065: Section heading: "Today in Your Garden" (UI-Element)
- Status: In Progress
- parent -> SCR-005

## UI-066: Horizontal scrollable task cards, per plant: (UI-Element)
- Status: In Progress
- parent -> SCR-005

## UI-067: Plant thumbnail + name (UI-Element)
- Status: In Progress
- parent -> SCR-005

## UI-068: Task type chip (UI-Element)
Water / Feed / Prune / Check / Harvest
- Status: In Progress
- parent -> SCR-005

## UI-069: Done ✓ button (UI-Element)
tap to complete
- Status: In Progress
- parent -> SCR-005

## UI-070: "All done today!" celebration state (UI-Element)
animated confetti, hidden by default
- Status: In Progress
- parent -> SCR-005

## UI-071: "See full schedule →" link (UI-Element)
→ SCR-07 Smart Scheduler
- Status: In Progress
- parent -> SCR-005

## UI-072: Circular score dial (UI-Element)
0–100) with colour zone (red / amber / green
- Status: In Progress
- parent -> SCR-005

## UI-073: 3 top metric labels (UI-Element)
e.g., Moisture · Light · pH
- Status: In Progress
- parent -> SCR-005

## UI-074: View Details → link (UI-Element)
→ SCR-11 Profile & Badges
- Status: In Progress
- parent -> SCR-005

## UI-075: Section heading: "My Garden" + See All → link (UI-Element)
→ SCR-02
- Status: In Progress
- parent -> SCR-005

## UI-076: Horizontal scroll: plant thumbnail cards (UI-Element)
- Status: In Progress
- parent -> SCR-005

## UI-077: Plant photo, plant name, health dot indicator (UI-Element)
green / amber / red
- Status: In Progress
- parent -> SCR-005

## UI-078: Tap → SCR-03 Plant Detail (UI-Element)
- Status: In Progress
- parent -> SCR-005

## UI-079: "💡 From your garden expert" header label (UI-Element)
- Status: In Progress
- parent -> SCR-005

## UI-080: Article title + method tag (UI-Element)
- Status: In Progress
- parent -> SCR-005

## UI-081: Estimated read time label (UI-Element)
- Status: In Progress
- parent -> SCR-005

## UI-082: Tap → MOD-09 Tip Article Reader Sheet (UI-Element)
- Status: In Progress
- parent -> SCR-005

## UI-083: "Your weekly report is ready 📊" label (UI-Element)
- Status: In Progress
- parent -> SCR-005

## UI-084: View Report button → MOD-11 Weekly Bloom Report Sheet (UI-Element)
`View Report` button → MOD-11 Weekly Bloom Report Sheet
- Status: In Progress
- parent -> SCR-005

## UI-085: -- (UI-Element)
- Status: In Progress
- parent -> SCR-005

## UI-086: -- (UI-Element)
- Status: In Progress
- parent -> SCR-005

## UI-087: *Tab:** Garden (UI-Element)
Tab 2
- Status: In Progress
- parent -> SCR-006

## UI-088: *Purpose:** All plants at a glance; entry point to per-plant management (UI-Element)
- Status: In Progress
- parent -> SCR-006

## UI-089: *Header / AppBar** (UI-Element)
- Status: In Progress
- parent -> SCR-006

## UI-090: "My Garden" title (UI-Element)
- Status: In Progress
- parent -> SCR-006

## UI-091: Filter / sort icon (UI-Element)
sort by: name / health / method / last logged
- Status: In Progress
- parent -> SCR-006

## UI-092: + Add Plant icon button (top-right) → MOD-02 Add / Edit Plant Sheet (UI-Element)
`+` Add Plant icon button (top-right) → MOD-02 Add / Edit Plant Sheet
- Status: In Progress
- parent -> SCR-006

## UI-093: *Filters** (UI-Element)
- Status: In Progress
- parent -> SCR-006

## UI-094: Growing method filter chips (horizontal scroll): All · Soil · Container · Hydro · Indoor (UI-Element)
- Status: In Progress
- parent -> SCR-006

## UI-095: *Main Content** (UI-Element)
- Status: In Progress
- parent -> SCR-006

## UI-096: Plant photo thumbnail (UI-Element)
- Status: In Progress
- parent -> SCR-006

## UI-097: Plant name (UI-Element)
common + nickname
- Status: In Progress
- parent -> SCR-006

## UI-098: Method badge chip (UI-Element)
Soil / Container / Hydro / Indoor
- Status: In Progress
- parent -> SCR-006

## UI-099: Health dot indicator (UI-Element)
colour-coded: green / amber / red
- Status: In Progress
- parent -> SCR-006

## UI-100: "Last logged X days ago" label (UI-Element)
- Status: In Progress
- parent -> SCR-006

## UI-101: Swipe-left actions: Archive (with confirm dialog) · Quick Log (UI-Element)
- Status: In Progress
- parent -> SCR-006

## UI-102: Empty state: illustrated pot graphic + "No plants yet" heading + Add Your First Plant button → MOD-02 (UI-Element)
Empty state: illustrated pot graphic + "No plants yet" heading + `Add Your First Plant` button → MOD-02
- Status: In Progress
- parent -> SCR-006

## UI-103: *Multi-Zone Management Unlocked State** (UI-Element)
visible only after referral unlock
- Status: In Progress
- parent -> SCR-006

## UI-104: Zone group headers above plant cards: "Windowsill" · "Balcony" · "Hydro Tent" etc. (UI-Element)
- Status: In Progress
- parent -> SCR-006

## UI-105: Plants grouped under their assigned zone; zone header is collapsible (UI-Element)
- Status: In Progress
- parent -> SCR-006

## UI-106: *Batch Mode** (UI-Element)
activates via header toggle → MOD-08
- Status: In Progress
- parent -> SCR-006

## UI-107: Select All button (UI-Element)
replaces header sort icon
- Status: In Progress
- parent -> SCR-006

## UI-108: Batch action bar at bottom: Water All · Feed All · Log Entry · Archive (UI-Element)
Batch action bar at bottom: `Water All` · `Feed All` · `Log Entry` · `Archive`
- Status: In Progress
- parent -> SCR-006

## UI-109: *Modals Triggered** (UI-Element)
- Status: In Progress
- parent -> SCR-006

## UI-110: MOD-02 Add / Edit Plant Sheet (UI-Element)
via `+` header button
- Status: In Progress
- parent -> SCR-006

## UI-111: MOD-08 Batch Mode Overlay (UI-Element)
via batch toggle
- Status: In Progress
- parent -> SCR-006

## UI-112: MOD-01 Quick Log Sheet (UI-Element)
via FAB or swipe action
- Status: In Progress
- parent -> SCR-006

## UI-113: -- (UI-Element)
- Status: In Progress
- parent -> SCR-006

## UI-114: *Tab:** Garden (UI-Element)
Tab 2, child of SCR-02
- Status: In Progress
- parent -> SCR-007

## UI-115: *Purpose:** Full per-plant management — logs, health, care, diagnostics, sharing (UI-Element)
- Status: In Progress
- parent -> SCR-007

## UI-116: *Header / AppBar** (UI-Element)
- Status: In Progress
- parent -> SCR-007

## UI-117: Plant name (UI-Element)
title
- Status: In Progress
- parent -> SCR-007

## UI-118: ⋮ overflow menu: Edit Plant · Archive to Cemetery · Delete (UI-Element)
`⋮` overflow menu: Edit Plant · Archive to Cemetery · Delete
- Status: In Progress
- parent -> SCR-007

## UI-119: *Hero Area** (UI-Element)
- Status: In Progress
- parent -> SCR-007

## UI-120: Full-width plant photo (UI-Element)
tappable → SCR-15 Progress Reels Gallery
- Status: In Progress
- parent -> SCR-007

## UI-121: Photo count badge (UI-Element)
e.g., "12 photos"
- Status: In Progress
- parent -> SCR-007

## UI-122: 📷 Add Photo button overlay (UI-Element)
`📷 Add Photo` button overlay
- Status: In Progress
- parent -> SCR-007

## UI-123: *Action Pill Row** (UI-Element)
horizontal, always visible below hero
- Status: In Progress
- parent -> SCR-007

## UI-124: 📝 Log → MOD-01 Quick Log Sheet (UI-Element)
`📝 Log` → MOD-01 Quick Log Sheet
- Status: In Progress
- parent -> SCR-007

## UI-125: 🔬 Diagnose → SCR-06 Leaf Diagnostics (UI-Element)
`🔬 Diagnose` → SCR-06 Leaf Diagnostics
- Status: In Progress
- parent -> SCR-007

## UI-126: 📤 Share → MOD-12 Export / Share Sheet (UI-Element)
`📤 Share` → MOD-12 Export / Share Sheet
- Status: In Progress
- parent -> SCR-007

## UI-127: 💀 Archive → SCR-14 Cemetery Log (UI-Element)
with confirm dialog
- Status: In Progress
- parent -> SCR-007

## UI-128: *Plant Info Card** (UI-Element)
- Status: In Progress
- parent -> SCR-007

## UI-129: Species name + common name (UI-Element)
- Status: In Progress
- parent -> SCR-007

## UI-130: Method badge (UI-Element)
Soil / Container / Hydro / Indoor
- Status: In Progress
- parent -> SCR-007

## UI-131: Growing stage chip (UI-Element)
Seedling · Veg · Bloom · Fruiting · Dormant
- Status: In Progress
- parent -> SCR-007

## UI-132: Date added label (UI-Element)
- Status: In Progress
- parent -> SCR-007

## UI-133: Location / zone tag (UI-Element)
auto-detected from device, zone-level only
- Status: In Progress
- parent -> SCR-007

## UI-134: Container size (UI-Element)
conditional — shown if Container method selected
- Status: In Progress
- parent -> SCR-007

## UI-135: Edit icon → MOD-02 Add / Edit Plant Sheet (UI-Element)
pre-filled with existing data
- Status: In Progress
- parent -> SCR-007

## UI-136: *Health Section** (UI-Element)
- Status: In Progress
- parent -> SCR-007

## UI-137: Garden Health Score™ mini-dial (UI-Element)
this plant's individual score
- Status: In Progress
- parent -> SCR-007

## UI-138: 8-metric breakdown (expandable row): Moisture · Light · pH · Growth Rate · Nutrient Level · Pest Risk · Temperature · Humidity (UI-Element)
- Status: In Progress
- parent -> SCR-007

## UI-139: View Full Insights → expands inline chart (UI-Element)
`View Full Insights →` expands inline chart
- Status: In Progress
- parent -> SCR-007

## UI-140: *Weather Impact Banner** (UI-Element)
conditional — shown when weather affects this plant's care
- Status: In Progress
- parent -> SCR-007

## UI-141: Smart alert chip, e.g., "🌧 Rain in 2 days → skip next watering" (UI-Element)
- Status: In Progress
- parent -> SCR-007

## UI-142: *Today's Care Section** (UI-Element)
- Status: In Progress
- parent -> SCR-007

## UI-143: Reschedule link per task (UI-Element)
- Status: In Progress
- parent -> SCR-007

## UI-144: "View full schedule →" link → SCR-07 Smart Scheduler (UI-Element)
- Status: In Progress
- parent -> SCR-007

## UI-145: *Cross-Method Insight Card** (UI-Element)
conditional — shown when user grows same plant in multiple methods
- Status: In Progress
- parent -> SCR-007

## UI-146: e.g., "Your hydro basil grew 20% faster → try adjusting nutrients for soil batch" (UI-Element)
- Status: In Progress
- parent -> SCR-007

## UI-147: *Log History Timeline** (UI-Element)
- Status: In Progress
- parent -> SCR-007

## UI-148: Vertical timeline entries: (UI-Element)
- Status: In Progress
- parent -> SCR-007

## UI-149: Entry thumbnail (photo), timestamp, activity type chip, metric values logged (UI-Element)
- Status: In Progress
- parent -> SCR-007

## UI-150: Tap entry → expand detail (UI-Element)
full photo, notes, voice note playback
- Status: In Progress
- parent -> SCR-007

## UI-151: Load more button (UI-Element)
pagination
- Status: In Progress
- parent -> SCR-007

## UI-152: *Contextual Tip Card** (UI-Element)
- Status: In Progress
- parent -> SCR-007

## UI-153: Inline article suggestion based on last logged activity (UI-Element)
e.g., yellow leaves logged → "Magnesium Deficiency Guide"
- Status: In Progress
- parent -> SCR-007

## UI-154: Tap → MOD-09 Tip Article Reader Sheet (UI-Element)
- Status: In Progress
- parent -> SCR-007

## UI-155: *Notes Field** (UI-Element)
- Status: In Progress
- parent -> SCR-007

## UI-156: Freeform text area "Quick note…" (UI-Element)
- Status: In Progress
- parent -> SCR-007

## UI-157: *Modals Triggered** (UI-Element)
- Status: In Progress
- parent -> SCR-007

## UI-158: MOD-01 Quick Log Sheet (UI-Element)
- Status: In Progress
- parent -> SCR-007

## UI-159: MOD-02 Add / Edit Plant Sheet (UI-Element)
via Edit
- Status: In Progress
- parent -> SCR-007

## UI-160: MOD-04 Permission Context Modal (UI-Element)
mic — only on first mic icon tap if permission not granted
- Status: In Progress
- parent -> SCR-007

## UI-161: MOD-09 Tip Article Reader Sheet (UI-Element)
- Status: In Progress
- parent -> SCR-007

## UI-162: MOD-12 Export / Share Sheet (UI-Element)
- Status: In Progress
- parent -> SCR-007

## UI-163: -- (UI-Element)
- Status: In Progress
- parent -> SCR-007

## UI-164: *Tab:** Garden (UI-Element)
child of SCR-03) + Profile (child of SCR-11
- Status: In Progress
- parent -> SCR-008

## UI-165: *Purpose:** View, generate, and share growth timelapses and before/after reels (UI-Element)
- Status: In Progress
- parent -> SCR-008

## UI-166: *Header / AppBar** (UI-Element)
- Status: In Progress
- parent -> SCR-008

## UI-167: "My Reels" title (UI-Element)
- Status: In Progress
- parent -> SCR-008

## UI-168: + Create button (UI-Element)
top-right
- Status: In Progress
- parent -> SCR-008

## UI-169: *Filter Bar** (UI-Element)
- Status: In Progress
- parent -> SCR-008

## UI-170: Filter chips: All · By Plant · By Method · By Date (UI-Element)
- Status: In Progress
- parent -> SCR-008

## UI-171: *Main Content** (UI-Element)
- Status: In Progress
- parent -> SCR-008

## UI-172: Grid of reel cards (2-col): (UI-Element)
- Status: In Progress
- parent -> SCR-008

## UI-173: Video thumbnail with play icon overlay (UI-Element)
- Status: In Progress
- parent -> SCR-008

## UI-174: Plant name label (UI-Element)
- Status: In Progress
- parent -> SCR-008

## UI-175: Date range label (UI-Element)
e.g., "Mar–May 2026"
- Status: In Progress
- parent -> SCR-008

## UI-176: Duration label (UI-Element)
e.g., "0:18"
- Status: In Progress
- parent -> SCR-008

## UI-177: Share icon button (bottom-right of card) → MOD-12 Export / Share Sheet (UI-Element)
- Status: In Progress
- parent -> SCR-008

## UI-178: *Reel Playback Screen** (on tap of any card, full-screen view): (UI-Element)
- Status: In Progress
- parent -> SCR-008

## UI-179: Video player (UI-Element)
auto-play, muted by default
- Status: In Progress
- parent -> SCR-008

## UI-180: Method-specific data overlay (UI-Element)
method badge, key metrics logged during that period
- Status: In Progress
- parent -> SCR-008

## UI-181: GardenPulse watermark (UI-Element)
removable for Supporter Badge holders via MOD-07
- Status: In Progress
- parent -> SCR-008

## UI-182: Share button → MOD-12 Export / Share Sheet (UI-Element)
`Share` button → MOD-12 Export / Share Sheet
- Status: In Progress
- parent -> SCR-008

## UI-183: Download button → MOD-05 Rewarded Video Prompt (UI-Element)
`Download` button → MOD-05 Rewarded Video Prompt
- Status: In Progress
- parent -> SCR-008

## UI-184: Close (×) button (UI-Element)
- Status: In Progress
- parent -> SCR-008

## UI-185: *Generate Reel Flow** (on + Create tap): (UI-Element)
*Generate Reel Flow** (on `+ Create` tap):
- Status: In Progress
- parent -> SCR-008

## UI-186: Step 1: Plant selector (UI-Element)
your plants list
- Status: In Progress
- parent -> SCR-008

## UI-187: Step 2: Date range picker (UI-Element)
start date – end date
- Status: In Progress
- parent -> SCR-008

## UI-188: Step 3: Preview strip (UI-Element)
photo thumbnails in sequence, sourced from logged photos
- Status: In Progress
- parent -> SCR-008

## UI-189: Step 4: Overlay style selector (UI-Element)
method-specific overlays with key metric data — no music; no external media
- Status: In Progress
- parent -> SCR-008

## UI-190: Generate Reel button → loading animation → result card added to grid (UI-Element)
`Generate Reel` button → loading animation → result card added to grid
- Status: In Progress
- parent -> SCR-008

## UI-191: *Empty State** (UI-Element)
- Status: In Progress
- parent -> SCR-008

## UI-192: Illustration: film strip with sprout (UI-Element)
- Status: In Progress
- parent -> SCR-008

## UI-193: "No reels yet" heading (UI-Element)
- Status: In Progress
- parent -> SCR-008

## UI-194: "Your first reel needs at least 3 logged photos" sub-label (UI-Element)
- Status: In Progress
- parent -> SCR-008

## UI-195: Go to My Garden → CTA button → SCR-02 Plant List (UI-Element)
`Go to My Garden →` CTA button → SCR-02 Plant List
- Status: In Progress
- parent -> SCR-008

## UI-196: *Modals Triggered** (UI-Element)
- Status: In Progress
- parent -> SCR-008

## UI-197: MOD-05 Rewarded Video Prompt (UI-Element)
on Download
- Status: In Progress
- parent -> SCR-008

## UI-198: MOD-12 Export / Share Sheet (UI-Element)
on Share
- Status: In Progress
- parent -> SCR-008

## UI-199: -- (UI-Element)
- Status: In Progress
- parent -> SCR-008

## UI-200: -- (UI-Element)
- Status: In Progress
- parent -> SCR-008

## UI-201: *Tab:** Tools (UI-Element)
Tab 3
- Status: In Progress
- parent -> SCR-009

## UI-202: *Purpose:** Entry point to all productivity tools (UI-Element)
- Status: In Progress
- parent -> SCR-009

## UI-203: *Header / AppBar** (UI-Element)
- Status: In Progress
- parent -> SCR-009

## UI-204: "Tools" title (UI-Element)
- Status: In Progress
- parent -> SCR-009

## UI-205: Search icon (UI-Element)
filters tool cards inline by name
- Status: In Progress
- parent -> SCR-009

## UI-206: *Main Content** (UI-Element)
- Status: In Progress
- parent -> SCR-009

## UI-207: "Recently Used" section (conditional — visible after first tool use): (UI-Element)
- Status: In Progress
- parent -> SCR-009

## UI-208: Last-used tool card (UI-Element)
icon + name + "Open again →" link
- Status: In Progress
- parent -> SCR-009

## UI-209: Tool cards grid (2-col): (UI-Element)
- Status: In Progress
- parent -> SCR-009

## UI-210: Each tool card: icon, title, one-line description, Open → chevron (UI-Element)
Each tool card: icon, title, one-line description, `Open →` chevron
- Status: In Progress
- parent -> SCR-009

## UI-211: -- (UI-Element)
- Status: In Progress
- parent -> SCR-009

## UI-212: *Tab:** Tools (UI-Element)
child of SCR-04
- Status: In Progress
- parent -> SCR-010

## UI-213: *Purpose:** Precise nutrient dosing for any brand, growing method, and growth stage (UI-Element)
- Status: In Progress
- parent -> SCR-010

## UI-214: *Header / AppBar** (UI-Element)
- Status: In Progress
- parent -> SCR-010

## UI-215: "Recipe Calculator" title (UI-Element)
- Status: In Progress
- parent -> SCR-010

## UI-216: ℹ info icon (UI-Element)
tooltip: "All calculations are method-specific estimates"
- Status: In Progress
- parent -> SCR-010

## UI-217: *Input Form** (UI-Element)
- Status: In Progress
- parent -> SCR-010

## UI-218: Method selector (UI-Element)
pills (required): Soil Drench · Hydro Reservoir · Foliar Spray
- Status: In Progress
- parent -> SCR-010

## UI-219: Nutrient brand selector (UI-Element)
dropdown / search field: brand name autocomplete; `Scan label →` button → MOD-03 QR Scanner Overlay
- Status: In Progress
- parent -> SCR-010

## UI-220: Water volume input (UI-Element)
number field + unit toggle (L / gal)
- Status: In Progress
- parent -> SCR-010

## UI-221: Growth stage selector (UI-Element)
pills: Seedling · Veg / Grow · Bloom / Flower · Flush / Ripening
- Status: In Progress
- parent -> SCR-010

## UI-222: *Action** (UI-Element)
- Status: In Progress
- parent -> SCR-010

## UI-223: *Results Card** (UI-Element)
appears below CTA after calculation completes
- Status: In Progress
- parent -> SCR-010

## UI-224: Per-nutrient rows: nutrient name · dose amount · unit · colour-coded severity indicator (UI-Element)
- Status: In Progress
- parent -> SCR-010

## UI-225: pH target range band (UI-Element)
visual slider
- Status: In Progress
- parent -> SCR-010

## UI-226: EC / PPM target label (UI-Element)
- Status: In Progress
- parent -> SCR-010

## UI-227: Warnings / notes label (UI-Element)
e.g., "Reduce by 25% for seedlings"
- Status: In Progress
- parent -> SCR-010

## UI-228: Add to Schedule → link → SCR-07 Smart Scheduler (UI-Element)
`Add to Schedule →` link → SCR-07 Smart Scheduler
- Status: In Progress
- parent -> SCR-010

## UI-229: Export / Share button → MOD-05 Rewarded Video Prompt (for PDF export), then MOD-12 Export / Share Sheet (UI-Element)
`Export / Share` button → MOD-05 Rewarded Video Prompt (for PDF export), then MOD-12 Export / Share Sheet
- Status: In Progress
- parent -> SCR-010

## UI-230: *Contextual Tip Link** (UI-Element)
below results card, conditional
- Status: In Progress
- parent -> SCR-010

## UI-231: "While calculating, read: [related article title]" → MOD-09 Tip Article Reader Sheet (UI-Element)
- Status: In Progress
- parent -> SCR-010

## UI-232: *Modals Triggered** (UI-Element)
- Status: In Progress
- parent -> SCR-010

## UI-233: MOD-03 QR Scanner Overlay (UI-Element)
via "Scan label" button
- Status: In Progress
- parent -> SCR-010

## UI-234: MOD-06 Interstitial Ad (UI-Element)
on `Generate Recipe` tap
- Status: In Progress
- parent -> SCR-010

## UI-235: MOD-05 Rewarded Video Prompt (UI-Element)
on `Export PDF`
- Status: In Progress
- parent -> SCR-010

## UI-236: MOD-09 Tip Article Reader Sheet (UI-Element)
via contextual tip link
- Status: In Progress
- parent -> SCR-010

## UI-237: MOD-12 Export / Share Sheet (UI-Element)
after rewarded video
- Status: In Progress
- parent -> SCR-010

## UI-238: -- (UI-Element)
- Status: In Progress
- parent -> SCR-010

## UI-239: *Tab:** Tools (child of SCR-04) + accessible from SCR-03 Plant Detail action pill row (UI-Element)
- Status: In Progress
- parent -> SCR-011

## UI-240: *Purpose:** On-device AI plant ID, issue detection, and guided fix suggestions — no cloud upload (UI-Element)
- Status: In Progress
- parent -> SCR-011

## UI-241: *Permission Gate** (UI-Element)
- Status: In Progress
- parent -> SCR-011

## UI-242: If camera not yet granted: MOD-04 Permission Context Modal (camera) fires before camera UI is shown; explains on-device privacy promise before OS dialog (UI-Element)
- Status: In Progress
- parent -> SCR-011

## UI-243: *Header / AppBar** (UI-Element)
- Status: In Progress
- parent -> SCR-011

## UI-244: "Leaf Diagnostics" title (UI-Element)
- Status: In Progress
- parent -> SCR-011

## UI-245: History icon (top-right) → scrolls down to Past Diagnoses section (UI-Element)
`History` icon (top-right) → scrolls down to Past Diagnoses section
- Status: In Progress
- parent -> SCR-011

## UI-246: *Camera Area** (UI-Element)
shown after camera permission granted
- Status: In Progress
- parent -> SCR-011

## UI-247: Full-card camera viewfinder (UI-Element)
- Status: In Progress
- parent -> SCR-011

## UI-248: Alignment overlay: leaf-shaped guide frame with animated pulse border (UI-Element)
- Status: In Progress
- parent -> SCR-011

## UI-249: "Centre the leaf in frame" instruction label (UI-Element)
- Status: In Progress
- parent -> SCR-011

## UI-250: 🖼 Choose from Gallery link (UI-Element)
import existing photo as fallback — no cloud upload; analysis still on-device
- Status: In Progress
- parent -> SCR-011

## UI-251: *Scanning State** (UI-Element)
post-capture, while AI processes on-device
- Status: In Progress
- parent -> SCR-011

## UI-252: Full-screen loading overlay: "Analysing on-device…" label + animated scan line (UI-Element)
- Status: In Progress
- parent -> SCR-011

## UI-253: Privacy badge: "Your photo never leaves your device" (UI-Element)
- Status: In Progress
- parent -> SCR-011

## UI-254: *Results Card** (UI-Element)
replaces camera area after analysis completes
- Status: In Progress
- parent -> SCR-011

## UI-255: Plant name identified (common + scientific name) + confidence % badge (UI-Element)
- Status: In Progress
- parent -> SCR-011

## UI-256: Method detected label (UI-Element)
e.g., "Hydroponic — confirmed"
- Status: In Progress
- parent -> SCR-011

## UI-257: Primary issue card: (UI-Element)
- Status: In Progress
- parent -> SCR-011

## UI-258: Issue name (UI-Element)
e.g., "Magnesium Deficiency"
- Status: In Progress
- parent -> SCR-011

## UI-259: Confidence % badge (UI-Element)
- Status: In Progress
- parent -> SCR-011

## UI-260: Severity indicator chip: Low · Medium · High (UI-Element)
colour-coded
- Status: In Progress
- parent -> SCR-011

## UI-261: Brief explanation label (UI-Element)
2 lines
- Status: In Progress
- parent -> SCR-011

## UI-262: Secondary issues list (collapsed by default, expandable): additional findings (UI-Element)
- Status: In Progress
- parent -> SCR-011

## UI-263: Suggested actions list (UI-Element)
numbered steps
- Status: In Progress
- parent -> SCR-011

## UI-264: Contextual tip link: "Read: [related article title]" → MOD-09 Tip Article Reader Sheet (UI-Element)
- Status: In Progress
- parent -> SCR-011

## UI-265: Log This Diagnosis button → creates a log entry linked to the relevant plant in SCR-03 (UI-Element)
`Log This Diagnosis` button → creates a log entry linked to the relevant plant in SCR-03
- Status: In Progress
- parent -> SCR-011

## UI-266: Try Again / Retake button (UI-Element)
`Try Again / Retake` button
- Status: In Progress
- parent -> SCR-011

## UI-267: 📤 Share Results button → MOD-12 Export / Share Sheet (UI-Element)
`📤 Share Results` button → MOD-12 Export / Share Sheet
- Status: In Progress
- parent -> SCR-011

## UI-268: *Past Diagnoses Section** (UI-Element)
below results card, or on `History` icon tap
- Status: In Progress
- parent -> SCR-011

## UI-269: Vertical list: date, thumbnail, plant name, finding label, severity badge (UI-Element)
- Status: In Progress
- parent -> SCR-011

## UI-270: Filter chips: All · Deficiency · Pest · Disease · Overwatering (UI-Element)
- Status: In Progress
- parent -> SCR-011

## UI-271: *Permission Denied State** (UI-Element)
shown if user previously denied and has not re-granted
- Status: In Progress
- parent -> SCR-011

## UI-272: Illustration + "Camera access needed" heading (UI-Element)
- Status: In Progress
- parent -> SCR-011

## UI-273: *Modals Triggered** (UI-Element)
- Status: In Progress
- parent -> SCR-011

## UI-274: MOD-04 Permission Context Modal (UI-Element)
camera, on entry if not granted
- Status: In Progress
- parent -> SCR-011

## UI-275: MOD-09 Tip Article Reader Sheet (UI-Element)
via contextual tip link in results
- Status: In Progress
- parent -> SCR-011

## UI-276: MOD-12 Export / Share Sheet (UI-Element)
via Share Results button
- Status: In Progress
- parent -> SCR-011

## UI-277: -- (UI-Element)
- Status: In Progress
- parent -> SCR-011

## UI-278: *Tab:** Tools (UI-Element)
child of SCR-04
- Status: In Progress
- parent -> SCR-012

## UI-279: *Purpose:** Weather-aware, timezone-correct care schedule across all plants (UI-Element)
- Status: In Progress
- parent -> SCR-012

## UI-280: *Header / AppBar** (UI-Element)
- Status: In Progress
- parent -> SCR-012

## UI-281: "My Schedule" title (UI-Element)
- Status: In Progress
- parent -> SCR-012

## UI-282: *Calendar View** (UI-Element)
- Status: In Progress
- parent -> SCR-012

## UI-283: Week strip (UI-Element)
default) or monthly grid (on toggle
- Status: In Progress
- parent -> SCR-012

## UI-284: Day cells: coloured dot per task type (UI-Element)
blue = water · green = feed · yellow = prune · red = urgent
- Status: In Progress
- parent -> SCR-012

## UI-285: Today's date highlight ring (UI-Element)
- Status: In Progress
- parent -> SCR-012

## UI-286: Sunrise / Sunset time labels (UI-Element)
derived from location data and local timezone
- Status: In Progress
- parent -> SCR-012

## UI-287: Tap a day cell → expands task list panel below (UI-Element)
- Status: In Progress
- parent -> SCR-012

## UI-288: *Task List Panel** (UI-Element)
for selected day
- Status: In Progress
- parent -> SCR-012

## UI-289: Per-task rows: (UI-Element)
- Status: In Progress
- parent -> SCR-012

## UI-290: Plant thumbnail + plant name (UI-Element)
- Status: In Progress
- parent -> SCR-012

## UI-291: Task type chip (UI-Element)
Water / Feed / Prune / Check / Harvest
- Status: In Progress
- parent -> SCR-012

## UI-292: Mark All Done bulk button (UI-Element)
day-level
- Status: In Progress
- parent -> SCR-012

## UI-293: *Smart Controls Panel** (UI-Element)
- Status: In Progress
- parent -> SCR-012

## UI-294: "I prefer reminders in the:" radio selector: Morning (UI-Element)
7–9 AM) · Afternoon (12–2 PM) · Evening (6–8 PM
- Status: In Progress
- parent -> SCR-012

## UI-295: *Add Custom Reminder Section** (UI-Element)
- Status: In Progress
- parent -> SCR-012

## UI-296: + Add Custom Reminder button → inline form: (UI-Element)
`+ Add Custom Reminder` button → inline form:
- Status: In Progress
- parent -> SCR-012

## UI-297: Plant selector (UI-Element)
dropdown from user's garden
- Status: In Progress
- parent -> SCR-012

## UI-298: Task type selector (UI-Element)
Water / Feed / Prune / Check / Harvest / Custom
- Status: In Progress
- parent -> SCR-012

## UI-299: Repeat selector (UI-Element)
Once · Daily · Weekly · Custom interval
- Status: In Progress
- parent -> SCR-012

## UI-300: Date + time picker (UI-Element)
timezone-aware, daylight saving auto-adjusted
- Status: In Progress
- parent -> SCR-012

## UI-301: *Quick Links** (UI-Element)
- Status: In Progress
- parent -> SCR-012

## UI-302: "Notification preferences →" link → MOD-10 Notification Prefs Sheet (UI-Element)
- Status: In Progress
- parent -> SCR-012

## UI-303: -- (UI-Element)
- Status: In Progress
- parent -> SCR-012

## UI-304: -- (UI-Element)
- Status: In Progress
- parent -> SCR-012

## UI-305: *Tab:** Community (UI-Element)
Tab 4
- Status: In Progress
- parent -> SCR-013

## UI-306: *Purpose:** Local insights, clusters, grow challenges, and community activity (UI-Element)
- Status: In Progress
- parent -> SCR-013

## UI-307: *Header / AppBar** (UI-Element)
- Status: In Progress
- parent -> SCR-013

## UI-308: "Community" title (UI-Element)
- Status: In Progress
- parent -> SCR-013

## UI-309: Search icon (UI-Element)
search clusters / challenges
- Status: In Progress
- parent -> SCR-013

## UI-310: *Top Banner** (UI-Element)
- Status: In Progress
- parent -> SCR-013

## UI-311: Local context card: "What's thriving in [City] right now 🌱" (UI-Element)
- Status: In Progress
- parent -> SCR-013

## UI-312: Anonymous insight label (UI-Element)
e.g., "Cherry tomatoes: 87% success rate in Berlin balconies"
- Status: In Progress
- parent -> SCR-013

## UI-313: View Map → link → SCR-10 Local Grow Map (UI-Element)
`View Map →` link → SCR-10 Local Grow Map
- Status: In Progress
- parent -> SCR-013

## UI-314: *Tab Bar** (horizontal, inside screen — 3 tabs): (UI-Element)
- Status: In Progress
- parent -> SCR-013

## UI-315: Local (UI-Element)
(default)
- Status: In Progress
- parent -> SCR-013

## UI-316: *Local Tab Content** (UI-Element)
- Status: In Progress
- parent -> SCR-013

## UI-317: Success stats cards: plant name · success % · grower count · trending arrow (UI-Element)
- Status: In Progress
- parent -> SCR-013

## UI-318: "In your zone" filter badge (UI-Element)
location-aware, zone-level only
- Status: In Progress
- parent -> SCR-013

## UI-319: View Full Map → button → SCR-10 Local Grow Map (UI-Element)
`View Full Map →` button → SCR-10 Local Grow Map
- Status: In Progress
- parent -> SCR-013

## UI-320: *Clusters Tab Content** (UI-Element)
- Status: In Progress
- parent -> SCR-013

## UI-321: "My Clusters" section: joined cluster cards → SCR-09 Garden Cluster Detail (UI-Element)
- Status: In Progress
- parent -> SCR-013

## UI-322: "Nearby Clusters" section: suggested clusters (UI-Element)
by zone / growing method
- Status: In Progress
- parent -> SCR-013

## UI-323: + Join a Cluster CTA button → cluster search / browse sheet (UI-Element)
inline
- Status: In Progress
- parent -> SCR-013

## UI-324: Each cluster card: cluster name, member count, method tag, recent activity indicator, Join or Joined button (UI-Element)
Each cluster card: cluster name, member count, method tag, recent activity indicator, `Join` or `Joined` button
- Status: In Progress
- parent -> SCR-013

## UI-325: *Challenges Tab Content** (UI-Element)
- Status: In Progress
- parent -> SCR-013

## UI-326: Current weekly challenge card: (UI-Element)
- Status: In Progress
- parent -> SCR-013

## UI-327: Challenge title (UI-Element)
e.g., "Best Regrowth from Kitchen Scraps"
- Status: In Progress
- parent -> SCR-013

## UI-328: End date countdown label (UI-Element)
- Status: In Progress
- parent -> SCR-013

## UI-329: Entry count label (UI-Element)
- Status: In Progress
- parent -> SCR-013

## UI-330: Submit Entry button → MOD-01 Quick Log Sheet (UI-Element)
photo + caption pre-labelled for challenge
- Status: In Progress
- parent -> SCR-013

## UI-331: Past challenges section: winner spotlight cards (UI-Element)
anonymized photo, method badge, prize label, featured user label
- Status: In Progress
- parent -> SCR-013

## UI-332: *Referral Banner** (UI-Element)
bottom of screen, persistent
- Status: In Progress
- parent -> SCR-013

## UI-333: "Invite 3 friends → unlock Multi-Zone Management" (UI-Element)
- Status: In Progress
- parent -> SCR-013

## UI-334: Progress indicator: X / 3 friends invited (UI-Element)
- Status: In Progress
- parent -> SCR-013

## UI-335: Share Invite Link button → MOD-12 Export / Share Sheet (UI-Element)
`Share Invite Link` button → MOD-12 Export / Share Sheet
- Status: In Progress
- parent -> SCR-013

## UI-336: -- (UI-Element)
- Status: In Progress
- parent -> SCR-013

## UI-337: *Tab:** Community (UI-Element)
child of SCR-08
- Status: In Progress
- parent -> SCR-014

## UI-338: *Purpose:** Community space for a specific interest- or location-based group (UI-Element)
- Status: In Progress
- parent -> SCR-014

## UI-339: *Header / AppBar** (UI-Element)
- Status: In Progress
- parent -> SCR-014

## UI-340: Cluster name (UI-Element)
title
- Status: In Progress
- parent -> SCR-014

## UI-341: ⋮ overflow menu: Report Cluster · Share Cluster (UI-Element)
→ MOD-12
- Status: In Progress
- parent -> SCR-014

## UI-342: *Cluster Info Section** (UI-Element)
- Status: In Progress
- parent -> SCR-014

## UI-343: Cluster cover image (UI-Element)
or default zone-based gradient
- Status: In Progress
- parent -> SCR-014

## UI-344: Member count label · Location or interest tag · Creation date (UI-Element)
- Status: In Progress
- parent -> SCR-014

## UI-345: Description text (UI-Element)
2–3 lines, expandable
- Status: In Progress
- parent -> SCR-014

## UI-346: *Tab Bar** (inside screen — 4 tabs): (UI-Element)
- Status: In Progress
- parent -> SCR-014

## UI-347: Posts (UI-Element)
(default)
- Status: In Progress
- parent -> SCR-014

## UI-348: *Posts Tab Content** (UI-Element)
- Status: In Progress
- parent -> SCR-014

## UI-349: Post feed (vertical scroll): (UI-Element)
- Status: In Progress
- parent -> SCR-014

## UI-350: Anonymized avatar + username handle (UI-Element)
- Status: In Progress
- parent -> SCR-014

## UI-351: Post text (UI-Element)
method-tagged
- Status: In Progress
- parent -> SCR-014

## UI-352: Optional plant photo (UI-Element)
tap to expand full-screen
- Status: In Progress
- parent -> SCR-014

## UI-353: Method badge chip (UI-Element)
- Status: In Progress
- parent -> SCR-014

## UI-354: 👍 Like button + 💬 Comment button (UI-Element)
comment count label
- Status: In Progress
- parent -> SCR-014

## UI-355: ⚑ Report icon (UI-Element)
per post, for moderation
- Status: In Progress
- parent -> SCR-014

## UI-356: Full-screen photo viewer (on photo tap): Log this plant → CTA → MOD-02 Add / Edit Plant Sheet pre-filled with species (UI-Element)
Full-screen photo viewer (on photo tap): `Log this plant →` CTA → MOD-02 Add / Edit Plant Sheet pre-filled with species
- Status: In Progress
- parent -> SCR-014

## UI-357: Comment thread (UI-Element)
inline, expandable
- Status: In Progress
- parent -> SCR-014

## UI-358: *Members Tab Content** (UI-Element)
- Status: In Progress
- parent -> SCR-014

## UI-359: List of anonymized member rows: avatar + username + method badges + joined date (UI-Element)
- Status: In Progress
- parent -> SCR-014

## UI-360: "X members growing Y together" summary label (UI-Element)
- Status: In Progress
- parent -> SCR-014

## UI-361: *Challenges Tab Content** (UI-Element)
- Status: In Progress
- parent -> SCR-014

## UI-362: Active challenge card for this cluster (UI-Element)
- Status: In Progress
- parent -> SCR-014

## UI-363: Submit Entry button → MOD-01 Quick Log Sheet (UI-Element)
`Submit Entry` button → MOD-01 Quick Log Sheet
- Status: In Progress
- parent -> SCR-014

## UI-364: Text field: "Share with the cluster…" (UI-Element)
- Status: In Progress
- parent -> SCR-014

## UI-365: Camera icon (attach photo) → triggers MOD-04 Permission Context Modal (camera) if not yet granted, then opens camera (UI-Element)
- Status: In Progress
- parent -> SCR-014

## UI-366: @ Tag plants button (UI-Element)
links post to a plant in user's garden
- Status: In Progress
- parent -> SCR-014

## UI-367: Method selector chip (UI-Element)
- Status: In Progress
- parent -> SCR-014

## UI-368: Post submit button (UI-Element)
`Post` submit button
- Status: In Progress
- parent -> SCR-014

## UI-369: *Modals Triggered** (UI-Element)
- Status: In Progress
- parent -> SCR-014

## UI-370: MOD-01 Quick Log Sheet (UI-Element)
via challenge Submit Entry
- Status: In Progress
- parent -> SCR-014

## UI-371: MOD-04 Permission Context Modal (UI-Element)
camera, if attaching photo to post and permission not yet granted
- Status: In Progress
- parent -> SCR-014

## UI-372: MOD-12 Export / Share Sheet (UI-Element)
via cluster share in overflow menu
- Status: In Progress
- parent -> SCR-014

## UI-373: -- (UI-Element)
- Status: In Progress
- parent -> SCR-014

## UI-374: *Tab:** Community (UI-Element)
child of SCR-08
- Status: In Progress
- parent -> SCR-015

## UI-375: *Purpose:** Visual map of what's thriving anonymously in the user's region (UI-Element)
- Status: In Progress
- parent -> SCR-015

## UI-376: *Header / AppBar** (UI-Element)
- Status: In Progress
- parent -> SCR-015

## UI-377: "Local Grow Map" title (UI-Element)
- Status: In Progress
- parent -> SCR-015

## UI-378: *Map Area** (UI-Element)
full-width, ~60% of screen height
- Status: In Progress
- parent -> SCR-015

## UI-379: Interactive map (UI-Element)
zone overlays, base map tiles
- Status: In Progress
- parent -> SCR-015

## UI-380: Clustered success dots (colour by crop category): (UI-Element)
- Status: In Progress
- parent -> SCR-015

## UI-381: Tap cluster → expands to Map Cluster Popup Card (UI-Element)
bottom sheet — see below
- Status: In Progress
- parent -> SCR-015

## UI-382: User's location pin (UI-Element)
soft glow, zone-level precision only — not precise GPS pin, for privacy
- Status: In Progress
- parent -> SCR-015

## UI-383: Zoom / Pan controls (UI-Element)
standard map controls
- Status: In Progress
- parent -> SCR-015

## UI-384: Crop filter chips: All · Tomatoes · Herbs · Leafy Greens · Root Veg · Fruit · Hydro (UI-Element)
- Status: In Progress
- parent -> SCR-015

## UI-385: *Map Cluster Popup Card** (UI-Element)
bottom sheet, on cluster tap
- Status: In Progress
- parent -> SCR-015

## UI-386: Plant / crop name heading (UI-Element)
- Status: In Progress
- parent -> SCR-015

## UI-387: "X growers, Y% success rate" label (UI-Element)
- Status: In Progress
- parent -> SCR-015

## UI-388: "Top local tip:" label (UI-Element)
from most-upvoted community post in that zone
- Status: In Progress
- parent -> SCR-015

## UI-389: Method tag chips (UI-Element)
- Status: In Progress
- parent -> SCR-015

## UI-390: Grow This Plant → button → MOD-02 Add / Edit Plant Sheet, pre-filled with species (UI-Element)
`Grow This Plant →` button → MOD-02 Add / Edit Plant Sheet, pre-filled with species
- Status: In Progress
- parent -> SCR-015

## UI-391: View Cluster → link → SCR-09 Garden Cluster Detail (UI-Element)
related cluster for that zone / crop
- Status: In Progress
- parent -> SCR-015

## UI-392: *Stats Strip** (UI-Element)
below map area
- Status: In Progress
- parent -> SCR-015

## UI-393: "X plants being tracked in [City]" label (UI-Element)
- Status: In Progress
- parent -> SCR-015

## UI-394: "Most popular this season: [plant name]" label (UI-Element)
- Status: In Progress
- parent -> SCR-015

## UI-395: "Your zone: [Zone code]" badge (UI-Element)
- Status: In Progress
- parent -> SCR-015

## UI-396: *Privacy Footer** (UI-Element)
- Status: In Progress
- parent -> SCR-015

## UI-397: Padlock icon + "All data anonymized — location only shared at zone level" label (UI-Element)
- Status: In Progress
- parent -> SCR-015

## UI-398: Privacy settings → link → SCR-13 Privacy Dashboard (UI-Element)
`Privacy settings →` link → SCR-13 Privacy Dashboard
- Status: In Progress
- parent -> SCR-015

## UI-399: -- (UI-Element)
- Status: In Progress
- parent -> SCR-015

## UI-400: -- (UI-Element)
- Status: In Progress
- parent -> SCR-015

## UI-401: *Tab:** Profile (UI-Element)
Tab 5
- Status: In Progress
- parent -> SCR-016

## UI-402: *Purpose:** Personal identity, achievements, stats, streaks, and navigation to personal features (UI-Element)
- Status: In Progress
- parent -> SCR-016

## UI-403: *Header / AppBar** (UI-Element)
- Status: In Progress
- parent -> SCR-016

## UI-404: "My Profile" title (UI-Element)
- Status: In Progress
- parent -> SCR-016

## UI-405: *Profile Header Card** (UI-Element)
- Status: In Progress
- parent -> SCR-016

## UI-406: Avatar (UI-Element)
default illustrated leaf; tap to replace via camera or gallery
- Status: In Progress
- parent -> SCR-016

## UI-407: Username / display name (UI-Element)
editable inline
- Status: In Progress
- parent -> SCR-016

## UI-408: Growing profile tag: auto-generated from methods and location (UI-Element)
e.g., "Hydro + Balcony · Berlin"
- Status: In Progress
- parent -> SCR-016

## UI-409: Edit Profile link (UI-Element)
`Edit Profile` link
- Status: In Progress
- parent -> SCR-016

## UI-410: *Garden Health Score™ Card** (UI-Element)
- Status: In Progress
- parent -> SCR-016

## UI-411: Large circular dial (UI-Element)
overall score across all plants, 0–100
- Status: In Progress
- parent -> SCR-016

## UI-412: Score delta label: "+5 this week" (UI-Element)
- Status: In Progress
- parent -> SCR-016

## UI-413: View Breakdown → link → inline 8-metric accordion (UI-Element)
Moisture · Light · pH · Growth Rate · Nutrient Level · Pest Risk · Temperature · Humidity
- Status: In Progress
- parent -> SCR-016

## UI-414: *Stats Row** (UI-Element)
4 pill stats, horizontal scroll
- Status: In Progress
- parent -> SCR-016

## UI-415: Plants count (UI-Element)
active plants
- Status: In Progress
- parent -> SCR-016

## UI-416: Total log entries count (UI-Element)
- Status: In Progress
- parent -> SCR-016

## UI-417: Current streak (UI-Element)
days of consecutive logging
- Status: In Progress
- parent -> SCR-016

## UI-418: Challenges won count (UI-Element)
- Status: In Progress
- parent -> SCR-016

## UI-419: *Achievement Badges Grid** (UI-Element)
- Status: In Progress
- parent -> SCR-016

## UI-420: Earned badges (full colour): "Hydro Master" · "Balcony Boss" · "Zero-Waste Gardener" · "Streak: 30 Days" · method-specific badges (UI-Element)
- Status: In Progress
- parent -> SCR-016

## UI-421: Locked badges (greyed, with padlock icon): unlock criteria shown on tap (UI-Element)
- Status: In Progress
- parent -> SCR-016

## UI-422: Tap any badge → badge detail sheet (UI-Element)
earned date, unlock criteria, share button → MOD-12
- Status: In Progress
- parent -> SCR-016

## UI-423: *Confidence Score™ Section** (UI-Element)
optional, user-facing label: "My Skills"
- Status: In Progress
- parent -> SCR-016

## UI-424: 15-skill radial chart or horizontal bar list showing mastery level (UI-Element)
- Status: In Progress
- parent -> SCR-016

## UI-425: Skill examples: Watering · Nutrient Mixing · Pest ID · Pruning · pH Management · etc. (UI-Element)
- Status: In Progress
- parent -> SCR-016

## UI-426: "Track your mastery across 15 skills" sub-label (UI-Element)
- Status: In Progress
- parent -> SCR-016

## UI-427: *Streak Tracker** (UI-Element)
- Status: In Progress
- parent -> SCR-016

## UI-428: Current streak: fire icon + day count label (UI-Element)
- Status: In Progress
- parent -> SCR-016

## UI-429: Longest streak label (UI-Element)
- Status: In Progress
- parent -> SCR-016

## UI-430: Calendar heatmap (UI-Element)
last 30 days of logging activity, colour-coded by intensity
- Status: In Progress
- parent -> SCR-016

## UI-431: *Navigation Links** (UI-Element)
tappable row items
- Status: In Progress
- parent -> SCR-016

## UI-432: Progress Reels Gallery → SCR-15 (UI-Element)
- Status: In Progress
- parent -> SCR-016

## UI-433: Cemetery Log → SCR-14 (UI-Element)
- Status: In Progress
- parent -> SCR-016

## UI-434: Creator Studio → SCR-16 (UI-Element)
row label: "Earn from your guides"
- Status: In Progress
- parent -> SCR-016

## UI-435: *Referral Banner** (UI-Element)
- Status: In Progress
- parent -> SCR-016

## UI-436: "Invite 3 friends → unlock Multi-Zone Management" (UI-Element)
- Status: In Progress
- parent -> SCR-016

## UI-437: Progress bar: X / 3 friends invited (UI-Element)
- Status: In Progress
- parent -> SCR-016

## UI-438: Share Invite Link button → MOD-12 Export / Share Sheet (UI-Element)
`Share Invite Link` button → MOD-12 Export / Share Sheet
- Status: In Progress
- parent -> SCR-016

## UI-439: *Supporter Badge Banner** (UI-Element)
conditional — shown only if Supporter Badge not yet purchased
- Status: In Progress
- parent -> SCR-016

## UI-440: "$2.99 · Remove interstitial ads forever" label (UI-Element)
- Status: In Progress
- parent -> SCR-016

## UI-441: Learn More button → MOD-07 Supporter Badge Dialog (UI-Element)
`Learn More` button → MOD-07 Supporter Badge Dialog
- Status: In Progress
- parent -> SCR-016

## UI-442: -- (UI-Element)
- Status: In Progress
- parent -> SCR-016

## UI-443: *Tab:** Profile (UI-Element)
child of SCR-11
- Status: In Progress
- parent -> SCR-017

## UI-444: *Purpose:** App-wide preferences, appearance, privacy, accessibility, and account management (UI-Element)
- Status: In Progress
- parent -> SCR-017

## UI-445: *Header / AppBar** (UI-Element)
- Status: In Progress
- parent -> SCR-017

## UI-446: "Settings" title (UI-Element)
- Status: In Progress
- parent -> SCR-017

## UI-447: *Sections** (vertical grouped list with section headings): (UI-Element)
- Status: In Progress
- parent -> SCR-017

## UI-448: *1 · Profile & Growing Setup** (UI-Element)
- Status: In Progress
- parent -> SCR-017

## UI-449: Edit display name field (UI-Element)
- Status: In Progress
- parent -> SCR-017

## UI-450: Growing method preference multi-select chips: Soil · Container · Hydro · Indoor (UI-Element)
- Status: In Progress
- parent -> SCR-017

## UI-451: Location / zone field: auto-detected with manual override (UI-Element)
ZIP / postal code entry fallback
- Status: In Progress
- parent -> SCR-017

## UI-452: Unit system selector: Metric · Imperial (UI-Element)
auto-detected from device locale, manually overridable
- Status: In Progress
- parent -> SCR-017

## UI-453: *2 · Notifications** (UI-Element)
- Status: In Progress
- parent -> SCR-017

## UI-454: Notification Preferences → tappable row → MOD-10 Notification Prefs Sheet (UI-Element)
`Notification Preferences →` tappable row → MOD-10 Notification Prefs Sheet
- Status: In Progress
- parent -> SCR-017

## UI-455: *3 · Appearance** (UI-Element)
- Status: In Progress
- parent -> SCR-017

## UI-456: Font selector: Standard · Dyslexia-Friendly (UI-Element)
OpenDyslexic
- Status: In Progress
- parent -> SCR-017

## UI-457: Text size slider (UI-Element)
Small → Large, 5 steps
- Status: In Progress
- parent -> SCR-017

## UI-458: *4 · Accessibility** (UI-Element)
- Status: In Progress
- parent -> SCR-017

## UI-459: *5 · Language & Region** (UI-Element)
- Status: In Progress
- parent -> SCR-017

## UI-460: Language selector dropdown: English · German · French · Spanish · Dutch (UI-Element)
- Status: In Progress
- parent -> SCR-017

## UI-461: Date format selector: DD/MM/YYYY · MM/DD/YYYY (UI-Element)
- Status: In Progress
- parent -> SCR-017

## UI-462: *6 · Privacy & Data** (UI-Element)
- Status: In Progress
- parent -> SCR-017

## UI-463: Privacy Dashboard → tappable row → SCR-13 Privacy Dashboard (UI-Element)
`Privacy Dashboard →` tappable row → SCR-13 Privacy Dashboard
- Status: In Progress
- parent -> SCR-017

## UI-464: *7 · Monetisation** (UI-Element)
- Status: In Progress
- parent -> SCR-017

## UI-465: Supporter Badge — Remove Interstitial Ads tappable row → MOD-07 Supporter Badge Dialog (UI-Element)
`Supporter Badge — Remove Interstitial Ads` tappable row → MOD-07 Supporter Badge Dialog
- Status: In Progress
- parent -> SCR-017

## UI-466: *8 · Content & Tips** (UI-Element)
- Status: In Progress
- parent -> SCR-017

## UI-467: *9 · About** (UI-Element)
- Status: In Progress
- parent -> SCR-017

## UI-468: App version label (UI-Element)
- Status: In Progress
- parent -> SCR-017

## UI-469: Terms of Service link (UI-Element)
external
- Status: In Progress
- parent -> SCR-017

## UI-470: Privacy Policy link (UI-Element)
external
- Status: In Progress
- parent -> SCR-017

## UI-471: Rate GardenPulse ⭐ link (UI-Element)
→ App Store / Play Store listing
- Status: In Progress
- parent -> SCR-017

## UI-472: *10 · Account** (UI-Element)
red-tinted section
- Status: In Progress
- parent -> SCR-017

## UI-473: Export All My Data button (UI-Element)
GDPR/CCPA data export, delivered via email or download
- Status: In Progress
- parent -> SCR-017

## UI-474: Delete All My Data destructive button → confirmation dialog (UI-Element)
"This cannot be undone. Delete everything?"
- Status: In Progress
- parent -> SCR-017

## UI-475: Sign Out button (UI-Element)
`Sign Out` button
- Status: In Progress
- parent -> SCR-017

## UI-476: -- (UI-Element)
- Status: In Progress
- parent -> SCR-017

## UI-477: *Tab:** Profile (UI-Element)
child of SCR-12
- Status: In Progress
- parent -> SCR-018

## UI-478: *Purpose:** GDPR / CCPA compliance — transparent inventory of stored data with granular controls (UI-Element)
- Status: In Progress
- parent -> SCR-018

## UI-479: *Header / AppBar** (UI-Element)
- Status: In Progress
- parent -> SCR-018

## UI-480: "Your Data" title (UI-Element)
- Status: In Progress
- parent -> SCR-018

## UI-481: Last updated timestamp label (UI-Element)
top-right
- Status: In Progress
- parent -> SCR-018

## UI-482: *Data Inventory Section** (UI-Element)
- Status: In Progress
- parent -> SCR-018

## UI-483: Section heading: "What GardenPulse stores" (UI-Element)
- Status: In Progress
- parent -> SCR-018

## UI-484: Per-data-type rows (each expandable for detail): (UI-Element)
- Status: In Progress
- parent -> SCR-018

## UI-485: Location data (UI-Element)
last entry date, approximate zone stored (not precise GPS), `Clear` button
- Status: In Progress
- parent -> SCR-018

## UI-486: Plant logs (UI-Element)
entry count, storage size estimate, `Export` button + `Delete All` button
- Status: In Progress
- parent -> SCR-018

## UI-487: Photos (UI-Element)
count, total storage used, `Delete All` button
- Status: In Progress
- parent -> SCR-018

## UI-488: Voice logs (UI-Element)
count, storage used, `Delete All` button
- Status: In Progress
- parent -> SCR-018

## UI-489: Ad personalisation data (UI-Element)
current status label (on / off), `Opt Out` button
- Status: In Progress
- parent -> SCR-018

## UI-490: Section heading: "Control your data" (UI-Element)
- Status: In Progress
- parent -> SCR-018

## UI-491: Location sharing: on/off + description (UI-Element)
"Used for weather tips and zone detection"
- Status: In Progress
- parent -> SCR-018

## UI-492: Photo storage: on/off (UI-Element)
- Status: In Progress
- parent -> SCR-018

## UI-493: Voice log retention: on/off (UI-Element)
- Status: In Progress
- parent -> SCR-018

## UI-494: Ad personalisation: on/off (UI-Element)
- Status: In Progress
- parent -> SCR-018

## UI-495: Community anonymised data contribution: on/off (UI-Element)
- Status: In Progress
- parent -> SCR-018

## UI-496: *Legal Actions Section** (UI-Element)
- Status: In Progress
- parent -> SCR-018

## UI-497: Export My Data CTA button (UI-Element)
GDPR export, delivered as email or direct download
- Status: In Progress
- parent -> SCR-018

## UI-498: Delete All My Data destructive CTA button → confirmation dialog (UI-Element)
`Delete All My Data` destructive CTA button → confirmation dialog
- Status: In Progress
- parent -> SCR-018

## UI-499: *Links** (UI-Element)
- Status: In Progress
- parent -> SCR-018

## UI-500: Privacy Policy (UI-Element)
external link
- Status: In Progress
- parent -> SCR-018

## UI-501: Data processing agreements summary link (UI-Element)
external
- Status: In Progress
- parent -> SCR-018

## UI-502: *Pending Request Status** (UI-Element)
conditional
- Status: In Progress
- parent -> SCR-018

## UI-503: -- (UI-Element)
- Status: In Progress
- parent -> SCR-018

## UI-504: *Tab:** Profile (child of SCR-11) + accessible from SCR-03 Plant Detail action pill row (UI-Element)
- Status: In Progress
- parent -> SCR-019

## UI-505: *Purpose:** Historical log of failed grows to identify patterns and learn from losses (UI-Element)
- Status: In Progress
- parent -> SCR-019

## UI-506: *Header / AppBar** (UI-Element)
- Status: In Progress
- parent -> SCR-019

## UI-507: "Cemetery Log" title (UI-Element)
- Status: In Progress
- parent -> SCR-019

## UI-508: + Add icon button (top-right): manually log a plant that failed before app use (UI-Element)
`+ Add` icon button (top-right): manually log a plant that failed before app use
- Status: In Progress
- parent -> SCR-019

## UI-509: *Sub-heading** (UI-Element)
- Status: In Progress
- parent -> SCR-019

## UI-510: "Learn from every loss" italic label (UI-Element)
- Status: In Progress
- parent -> SCR-019

## UI-511: *Pattern Insight Card** (UI-Element)
conditional — shown after 2 or more entries
- Status: In Progress
- parent -> SCR-019

## UI-512: "🔍 Pattern detected: You've lost [N] plants to [cause]. Check your schedule." (UI-Element)
- Status: In Progress
- parent -> SCR-019

## UI-513: View Schedule → link → SCR-07 Smart Scheduler (UI-Element)
`View Schedule →` link → SCR-07 Smart Scheduler
- Status: In Progress
- parent -> SCR-019

## UI-514: *Filter Bar** (UI-Element)
- Status: In Progress
- parent -> SCR-019

## UI-515: Filter chips: All · By Method · By Cause · By Date (UI-Element)
- Status: In Progress
- parent -> SCR-019

## UI-516: *Empty State** (UI-Element)
- Status: In Progress
- parent -> SCR-019

## UI-517: Illustrated gravestone graphic (UI-Element)
- Status: In Progress
- parent -> SCR-019

## UI-518: "No failures recorded yet — keep growing! 🌱" label (UI-Element)
- Status: In Progress
- parent -> SCR-019

## UI-519: *Archived Plant Entries** (UI-Element)
vertical list
- Status: In Progress
- parent -> SCR-019

## UI-520: Per-entry card: (UI-Element)
- Status: In Progress
- parent -> SCR-019

## UI-521: Plant thumbnail + plant name (UI-Element)
- Status: In Progress
- parent -> SCR-019

## UI-522: Method badge (UI-Element)
- Status: In Progress
- parent -> SCR-019

## UI-523: Date archived label (UI-Element)
- Status: In Progress
- parent -> SCR-019

## UI-524: Cause of death (UI-Element)
selector (tap to edit):
- Status: In Progress
- parent -> SCR-019

## UI-525: "What I learned:" text field (UI-Element)
editable, includes `🎤` voice input icon — requests mic permission via MOD-04 if needed
- Status: In Progress
- parent -> SCR-019

## UI-526: Restore to Garden button (UI-Element)
moves plant back to SCR-02 Plant List if recovered
- Status: In Progress
- parent -> SCR-019

## UI-527: Delete Entry icon (UI-Element)
destructive, with confirm dialog
- Status: In Progress
- parent -> SCR-019

## UI-528: *Add Manually Section** (UI-Element)
- Status: In Progress
- parent -> SCR-019

## UI-529: + Log Manually CTA button → inline form: plant name, method, estimated date, cause of death, notes (UI-Element)
`+ Log Manually` CTA button → inline form: plant name, method, estimated date, cause of death, notes
- Status: In Progress
- parent -> SCR-019

## UI-530: *Export** (UI-Element)
- Status: In Progress
- parent -> SCR-019

## UI-531: Export Log as PDF button → MOD-05 Rewarded Video Prompt → MOD-12 Export / Share Sheet (UI-Element)
`Export Log as PDF` button → MOD-05 Rewarded Video Prompt → MOD-12 Export / Share Sheet
- Status: In Progress
- parent -> SCR-019

## UI-532: -- (UI-Element)
- Status: In Progress
- parent -> SCR-019

## UI-533: *Tab:** Profile (UI-Element)
child of SCR-11
- Status: In Progress
- parent -> SCR-020

## UI-534: *Access:** Visible to users who have enabled Creator Studio in SCR-12 Settings section 8 (UI-Element)
- Status: In Progress
- parent -> SCR-020

## UI-535: *Purpose:** Allow expert gardeners to write, publish, and earn AdMob revenue share from method-specific guides (UI-Element)
- Status: In Progress
- parent -> SCR-020

## UI-536: *Header / AppBar** (UI-Element)
- Status: In Progress
- parent -> SCR-020

## UI-537: "Creator Studio" title (UI-Element)
- Status: In Progress
- parent -> SCR-020

## UI-538: Publish button (UI-Element)
top-right, greyed until guide passes pre-publish check
- Status: In Progress
- parent -> SCR-020

## UI-539: *Revenue Info Banner** (UI-Element)
- Status: In Progress
- parent -> SCR-020

## UI-540: "✍ Write guides → earn AdMob revenue share" label (UI-Element)
- Status: In Progress
- parent -> SCR-020

## UI-541: Moderation notice: "All guides reviewed before going live (24–48 h)" (UI-Element)
- Status: In Progress
- parent -> SCR-020

## UI-542: Learn How It Works link (UI-Element)
inline info sheet
- Status: In Progress
- parent -> SCR-020

## UI-543: *Guide Editor Area** (UI-Element)
- Status: In Progress
- parent -> SCR-020

## UI-544: Cover image (UI-Element)
upload area: tap to capture via camera or import from gallery
- Status: In Progress
- parent -> SCR-020

## UI-545: Guide title (UI-Element)
text field (character limit 80)
- Status: In Progress
- parent -> SCR-020

## UI-546: Category / method (UI-Element)
multi-select chips: Soil · Hydro · Container · Indoor · Microgreen · Pest Control · Nutrition (and other method-relevant categories)
- Status: In Progress
- parent -> SCR-020

## UI-547: Tags (UI-Element)
field: free-form, max 5 tags, autocomplete from existing tag library
- Status: In Progress
- parent -> SCR-020

## UI-548: Rich text editor (UI-Element)
- Status: In Progress
- parent -> SCR-020

## UI-549: Toolbar: Bold · Italic · Heading (H2, H3) · Bullet list · Numbered list · Image insert · Divider (UI-Element)
- Status: In Progress
- parent -> SCR-020

## UI-550: Insert Plant Template shortcut button (UI-Element)
inserts standardised plant care table
- Status: In Progress
- parent -> SCR-020

## UI-551: Insert Tip Block shortcut (UI-Element)
styled callout block for tips / warnings
- Status: In Progress
- parent -> SCR-020

## UI-552: Full-screen expand mode (UI-Element)
- Status: In Progress
- parent -> SCR-020

## UI-553: Estimated read time (UI-Element)
label (auto-calculated, updates live as user types)
- Status: In Progress
- parent -> SCR-020

## UI-554: *Save / Submit Controls** (UI-Element)
- Status: In Progress
- parent -> SCR-020

## UI-555: Save Draft button (UI-Element)
saves locally and syncs to cloud
- Status: In Progress
- parent -> SCR-020

## UI-556: *My Published Guides Section** (UI-Element)
below editor, vertically scrollable
- Status: In Progress
- parent -> SCR-020

## UI-557: Guide cards: (UI-Element)
- Status: In Progress
- parent -> SCR-020

## UI-558: Guide thumbnail + title (UI-Element)
- Status: In Progress
- parent -> SCR-020

## UI-559: Status chip: Under Review · Live · Rejected (UI-Element)
with rejection reason shown for Rejected
- Status: In Progress
- parent -> SCR-020

## UI-560: View count label (UI-Element)
shown if Live
- Status: In Progress
- parent -> SCR-020

## UI-561: Edit button (UI-Element)
for Live guides: creates a new draft version; original stays live until new version approved
- Status: In Progress
- parent -> SCR-020

## UI-562: -- (UI-Element)
- Status: In Progress
- parent -> SCR-020

## UI-563: -- (UI-Element)
- Status: In Progress
- parent -> SCR-020

## UI-564: *Type:** Bottom sheet (UI-Element)
drag to expand to ~80% screen height
- Status: In Progress
- parent -> SCR-021

## UI-565: *Purpose:** Fastest possible logging — photo + activity type + one mood rating = complete log entry in minimal taps (UI-Element)
- Status: In Progress
- parent -> SCR-021

## UI-566: *Elements** (UI-Element)
- Status: In Progress
- parent -> SCR-021

## UI-567: Sheet drag handle bar (UI-Element)
- Status: In Progress
- parent -> SCR-021

## UI-568: "Quick Log" heading (UI-Element)
- Status: In Progress
- parent -> SCR-021

## UI-569: Plant selector (UI-Element)
horizontal scroll of plant cards (thumbnails + names); pre-filled if opened from SCR-03 Plant Detail; "All plants" option for multi-plant mode (used in Batch logging)
- Status: In Progress
- parent -> SCR-021

## UI-570: Photo area (UI-Element)
large tap-to-capture zone with camera icon; gallery import icon (bottom-left of area)
- Status: In Progress
- parent -> SCR-021

## UI-571: Activity type chips (UI-Element)
(multi-select): Water · Feed · Prune · Check · Harvest · Repot · Transplant · Note
- Status: In Progress
- parent -> SCR-021

## UI-572: "How did it go?" (UI-Element)
emoji slider (1 = 😟 → 5 = 😄)
- Status: In Progress
- parent -> SCR-021

## UI-573: Notes field (UI-Element)
"Add a quick note…" freeform text + `🎤` mic icon (voice input — requests MOD-04 mic permission if not yet granted)
- Status: In Progress
- parent -> SCR-021

## UI-574: Metric quick-entry (UI-Element)
(expandable optional row, collapsed by default):
- Status: In Progress
- parent -> SCR-021

## UI-575: pH slider · EC / PPM field · Moisture % field · Temperature field (UI-Element)
- Status: In Progress
- parent -> SCR-021

## UI-576: Cancel (UI-Element)
text link (below CTA)
- Status: In Progress
- parent -> SCR-021

## UI-577: -- (UI-Element)
- Status: In Progress
- parent -> SCR-021

## UI-578: *Type:** Bottom sheet (UI-Element)
large, ~90% height, step-scrollable
- Status: In Progress
- parent -> SCR-022

## UI-579: *Triggered from:** SCR-02 Plant List + header button · SCR-03 Plant Detail Edit icon · SCR-10 Local Grow Map "Grow This Plant →" button · SCR-09 full-screen photo viewer "Log this plant →" CTA (UI-Element)
*Triggered from:** SCR-02 Plant List `+` header button · SCR-03 Plant Detail `Edit` icon · SCR-10 Local Grow Map "Grow This Plant →" button · SCR-09 full-screen photo viewer "Log this plant →" CTA
- Status: In Progress
- parent -> SCR-022

## UI-580: *Purpose:** Add a new plant or edit an existing plant's metadata (UI-Element)
- Status: In Progress
- parent -> SCR-022

## UI-581: *Elements** (UI-Element)
- Status: In Progress
- parent -> SCR-022

## UI-582: Sheet drag handle bar (UI-Element)
- Status: In Progress
- parent -> SCR-022

## UI-583: "Add Plant" or "Edit Plant" heading (UI-Element)
dynamic, based on context
- Status: In Progress
- parent -> SCR-022

## UI-584: Browse by type (UI-Element)
grid: Herb · Vegetable · Fruit · Flower · Houseplant · Microgreen chips
- Status: In Progress
- parent -> SCR-022

## UI-585: Plant photo (UI-Element)
tap-to-capture thumbnail area + gallery import link
- Status: In Progress
- parent -> SCR-022

## UI-586: Nickname field (UI-Element)
"Give it a name (optional)" — character limit 30
- Status: In Progress
- parent -> SCR-022

## UI-587: Growing method selector (UI-Element)
pills (required): Soil · Container · Hydro · Indoor
- Status: In Progress
- parent -> SCR-022

## UI-588: Container / pot size field (UI-Element)
(conditional — shown only if Container method selected): volume field + unit toggle (L / gal)
- Status: In Progress
- parent -> SCR-022

## UI-589: Location / zone auto-tag (UI-Element)
zone badge displayed; `Change location` link for manual override
- Status: In Progress
- parent -> SCR-022

## UI-590: Cancel (UI-Element)
text link
- Status: In Progress
- parent -> SCR-022

## UI-591: *Modals Triggered** (UI-Element)
- Status: In Progress
- parent -> SCR-022

## UI-592: MOD-04 Permission Context Modal (UI-Element)
camera, on `Scan to identify` tap if camera not granted
- Status: In Progress
- parent -> SCR-022

## UI-593: -- (UI-Element)
- Status: In Progress
- parent -> SCR-022

## UI-594: *Type:** Camera overlay (UI-Element)
full-screen
- Status: In Progress
- parent -> SCR-023

## UI-595: *Triggered from:** SCR-04 Tools Hub (QR / Label Scanner card) · SCR-05 Calculator "Scan label →" button (UI-Element)
- Status: In Progress
- parent -> SCR-023

## UI-596: *Purpose:** Scan nutrient bottle labels, seed packets, or sensor QR codes for auto-fill into the Calculator or log (UI-Element)
- Status: In Progress
- parent -> SCR-023

## UI-597: *Elements** (UI-Element)
- Status: In Progress
- parent -> SCR-023

## UI-598: Full-screen camera feed (UI-Element)
live
- Status: In Progress
- parent -> SCR-023

## UI-599: Animated scan frame (UI-Element)
QR / barcode detection rectangle, pulsing border
- Status: In Progress
- parent -> SCR-023

## UI-600: "Point at a QR code or barcode" instruction label (UI-Element)
- Status: In Progress
- parent -> SCR-023

## UI-601: Enter code manually fallback text link (UI-Element)
bottom of screen
- Status: In Progress
- parent -> SCR-023

## UI-602: Success state (UI-Element)
(slides up as bottom card on scan detection):
- Status: In Progress
- parent -> SCR-023

## UI-603: Product thumbnail (UI-Element)
if found in database
- Status: In Progress
- parent -> SCR-023

## UI-604: Product name + brand label (UI-Element)
- Status: In Progress
- parent -> SCR-023

## UI-605: Product type chip: Nutrient · Seed · Sensor · Other (UI-Element)
- Status: In Progress
- parent -> SCR-023

## UI-606: Auto-fill action button: Fill Calculator → (UI-Element)
if opened from SCR-05) or `Log Scan →` (if opened from SCR-04
- Status: In Progress
- parent -> SCR-023

## UI-607: Scan Another link (UI-Element)
`Scan Another` link
- Status: In Progress
- parent -> SCR-023

## UI-608: -- (UI-Element)
- Status: In Progress
- parent -> SCR-023

## UI-609: *Type:** Modal dialog (UI-Element)
centre screen
- Status: In Progress
- parent -> SCR-024

## UI-610: *Triggered from:** (UI-Element)
- Status: In Progress
- parent -> SCR-024

## UI-611: SCR-06 Leaf Diagnostics: camera — fires on screen entry if camera not granted (UI-Element)
- Status: In Progress
- parent -> SCR-024

## UI-612: SCR-09 Cluster Detail post compose: camera — fires on photo attach tap if camera not granted (UI-Element)
- Status: In Progress
- parent -> SCR-024

## UI-613: *Purpose:** Contextual pre-prompt shown BEFORE the OS permission dialog — explains the value and privacy stance so users can make an informed decision (UI-Element)
- Status: In Progress
- parent -> SCR-024

## UI-614: *Elements** (UI-Element)
content adapts per permission type
- Status: In Progress
- parent -> SCR-024

## UI-615: Contextual illustration (changes per type): (UI-Element)
- Status: In Progress
- parent -> SCR-024

## UI-616: Location: map pin with leaf (UI-Element)
- Status: In Progress
- parent -> SCR-024

## UI-617: Camera: camera lens with leaf (UI-Element)
- Status: In Progress
- parent -> SCR-024

## UI-618: Microphone: mic with waveform (UI-Element)
- Status: In Progress
- parent -> SCR-024

## UI-619: Notifications: bell with leaf (UI-Element)
- Status: In Progress
- parent -> SCR-024

## UI-620: Title (UI-Element)
"Before we ask…" (location) · "Use your camera?" (camera) · "Voice logging?" (mic) · "Stay on top of your garden?" (notifications)
- Status: In Progress
- parent -> SCR-024

## UI-621: Benefit description (UI-Element)
2-sentence explanation of why this permission helps (e.g., "GardenPulse uses location to give weather-aware care tips. You can change this any time in Settings.")
- Status: In Progress
- parent -> SCR-024

## UI-622: Privacy reassurance label (UI-Element)
padlock icon + short reassurance (e.g., "Location never shared publicly without explicit opt-in")
- Status: In Progress
- parent -> SCR-024

## UI-623: Allow [Permission] (UI-Element)
primary CTA button → triggers OS system permission dialog immediately after tap
- Status: In Progress
- parent -> SCR-024

## UI-624: Not Now (UI-Element)
secondary text link (dismisses modal; app provides graceful fallback)
- Status: In Progress
- parent -> SCR-024

## UI-625: Learn more about privacy → (UI-Element)
text link (→ SCR-13 Privacy Dashboard)
- Status: In Progress
- parent -> SCR-024

## UI-626: *Denied State Variant** (banner, shown if permission was previously denied by OS): (UI-Element)
- Status: In Progress
- parent -> SCR-024

## UI-627: Warning icon + "[Permission] access is off" label (UI-Element)
- Status: In Progress
- parent -> SCR-024

## UI-628: *Rules (from brief)** (UI-Element)
- Status: In Progress
- parent -> SCR-024

## UI-629: Never display this modal on top of another permission dialog (UI-Element)
- Status: In Progress
- parent -> SCR-024

## UI-630: Never shown on onboarding screens for permissions not yet relevant to that step (UI-Element)
- Status: In Progress
- parent -> SCR-024

## UI-631: -- (UI-Element)
- Status: In Progress
- parent -> SCR-024

## UI-632: *Type:** Modal dialog (UI-Element)
centre screen
- Status: In Progress
- parent -> SCR-025

## UI-633: *Triggered from:** SCR-05 Calculator Export / Share → PDF export · SCR-15 Reels Gallery Download button · SCR-14 Cemetery Log Export Log as PDF button (UI-Element)
*Triggered from:** SCR-05 Calculator `Export / Share` → PDF export · SCR-15 Reels Gallery `Download` button · SCR-14 Cemetery Log `Export Log as PDF` button
- Status: In Progress
- parent -> SCR-025

## UI-634: *Purpose:** User willingly watches a short ad in exchange for a premium export unlock — value-exchange is transparent and truly optional (UI-Element)
- Status: In Progress
- parent -> SCR-025

## UI-635: *Elements** (UI-Element)
- Status: In Progress
- parent -> SCR-025

## UI-636: Video play icon graphic (UI-Element)
large, centre
- Status: In Progress
- parent -> SCR-025

## UI-637: Heading (UI-Element)
"Unlock [X]" (dynamic: "PDF Export" · "HD Download" · "Compliance Log PDF")
- Status: In Progress
- parent -> SCR-025

## UI-638: Sub-label (UI-Element)
"Watch a 30-second video to unlock this for free"
- Status: In Progress
- parent -> SCR-025

## UI-639: Estimated duration label: "~30 seconds" (UI-Element)
- Status: In Progress
- parent -> SCR-025

## UI-640: *During Video** (UI-Element)
- Status: In Progress
- parent -> SCR-025

## UI-641: Video player (UI-Element)
full-screen, AdMob rewarded unit
- Status: In Progress
- parent -> SCR-025

## UI-642: Progress timer label (UI-Element)
countdown
- Status: In Progress
- parent -> SCR-025

## UI-643: Skip button (UI-Element)
appears after AdMob-required minimum watch time
- Status: In Progress
- parent -> SCR-025

## UI-644: *Success State** (UI-Element)
after video completes
- Status: In Progress
- parent -> SCR-025

## UI-645: Animated unlock visual (UI-Element)
leaf + sparkle
- Status: In Progress
- parent -> SCR-025

## UI-646: "Unlocked! Your [X] is ready." heading (UI-Element)
- Status: In Progress
- parent -> SCR-025

## UI-647: Download / Export Now CTA button → MOD-12 Export / Share Sheet (UI-Element)
`Download / Export Now` CTA button → MOD-12 Export / Share Sheet
- Status: In Progress
- parent -> SCR-025

## UI-648: Auto-dismisses after 3 s if no tap (UI-Element)
- Status: In Progress
- parent -> SCR-025

## UI-649: -- (UI-Element)
- Status: In Progress
- parent -> SCR-025

## UI-650: *Type:** Full-screen ad overlay (UI-Element)
- Status: In Progress
- parent -> SCR-026

## UI-651: *Triggered from:** SCR-05 Nutrient / Recipe Calculator on Generate Recipe tap — appears during the 1.5 s loading animation while calculation runs (UI-Element)
*Triggered from:** SCR-05 Nutrient / Recipe Calculator on `Generate Recipe` tap — appears during the 1.5 s loading animation while calculation runs
- Status: In Progress
- parent -> SCR-026

## UI-652: *Purpose:** High-intent monetisation at a natural calculation latency moment (UI-Element)
- Status: In Progress
- parent -> SCR-026

## UI-653: *Elements** (UI-Element)
- Status: In Progress
- parent -> SCR-026

## UI-654: Full-screen AdMob interstitial unit (UI-Element)
- Status: In Progress
- parent -> SCR-026

## UI-655: "Ad · Powered by AdMob" attribution label (UI-Element)
footer
- Status: In Progress
- parent -> SCR-026

## UI-656: *Rules (per brief)** (UI-Element)
- Status: In Progress
- parent -> SCR-026

## UI-657: Never show on: permission request screens · onboarding screens · error / crisis states (UI-Element)
- Status: In Progress
- parent -> SCR-026

## UI-658: Appears at most once per Calculator session (UI-Element)
not on repeated `Generate Recipe` taps within the same session
- Status: In Progress
- parent -> SCR-026

## UI-659: -- (UI-Element)
- Status: In Progress
- parent -> SCR-026

## UI-660: *Type:** Modal dialog (UI-Element)
centre screen
- Status: In Progress
- parent -> SCR-027

## UI-661: *Triggered from:** SCR-12 Settings (UI-Element)
Monetisation row) · SCR-11 Profile & Badges (Supporter Badge banner
- Status: In Progress
- parent -> SCR-027

## UI-662: *Elements** (UI-Element)
- Status: In Progress
- parent -> SCR-027

## UI-663: Supporter leaf badge graphic (UI-Element)
animated shimmer
- Status: In Progress
- parent -> SCR-027

## UI-664: Heading (UI-Element)
"Support GardenPulse 🌿"
- Status: In Progress
- parent -> SCR-027

## UI-665: Price label (UI-Element)
"$2.99 · One-time · No subscription"
- Status: In Progress
- parent -> SCR-027

## UI-666: What you get list (UI-Element)
- Status: In Progress
- parent -> SCR-027

## UI-667: ✓ Interstitial ads removed forever (UI-Element)
- Status: In Progress
- parent -> SCR-027

## UI-668: ✓ Supporter Badge displayed on your profile (UI-Element)
- Status: In Progress
- parent -> SCR-027

## UI-669: ✓ GardenPulse watermark removal on exports (UI-Element)
- Status: In Progress
- parent -> SCR-027

## UI-670: "What stays" note (UI-Element)
(grey text): "Tips and native content remain — they help us improve the app"
- Status: In Progress
- parent -> SCR-027

## UI-671: Restore Purchase text link (UI-Element)
for users who reinstalled or switched devices
- Status: In Progress
- parent -> SCR-027

## UI-672: Not Now text link (UI-Element)
dismisses without purchase
- Status: In Progress
- parent -> SCR-027

## UI-673: -- (UI-Element)
- Status: In Progress
- parent -> SCR-027

## UI-674: *Type:** Overlay bar + transformed list (UI-Element)
activates in-place on SCR-02 Plant List
- Status: In Progress
- parent -> SCR-028

## UI-675: *Purpose:** Log or act on multiple plants at once with minimal taps (UI-Element)
- Status: In Progress
- parent -> SCR-028

## UI-676: *Elements** (UI-Element)
- Status: In Progress
- parent -> SCR-028

## UI-677: Top action bar (UI-Element)
(replaces normal header):
- Status: In Progress
- parent -> SCR-028

## UI-678: "Batch Mode" label + selected count badge (UI-Element)
e.g., "3 selected"
- Status: In Progress
- parent -> SCR-028

## UI-679: Select All button (UI-Element)
`Select All` button
- Status: In Progress
- parent -> SCR-028

## UI-680: ✕ Cancel button (UI-Element)
exits batch mode, restores normal header
- Status: In Progress
- parent -> SCR-028

## UI-681: Plant list transforms (UI-Element)
each plant card gains a checkbox overlay (multi-select)
- Status: In Progress
- parent -> SCR-028

## UI-682: Bottom action bar (UI-Element)
(appears when 1 or more plants are selected):
- Status: In Progress
- parent -> SCR-028

## UI-683: 💧 Water All button (UI-Element)
`💧 Water All` button
- Status: In Progress
- parent -> SCR-028

## UI-684: 🧪 Feed All button (UI-Element)
`🧪 Feed All` button
- Status: In Progress
- parent -> SCR-028

## UI-685: 📝 Log Entry button → opens MOD-01 Quick Log Sheet in multi-plant mode (UI-Element)
Plant selector pre-filled with selected plants
- Status: In Progress
- parent -> SCR-028

## UI-686: 💀 Archive button (UI-Element)
`💀 Archive` button
- Status: In Progress
- parent -> SCR-028

## UI-687: Confirmation dialog (UI-Element)
(before any batch action executes): "Apply [action] to [N] plants?" with `Confirm` + `Cancel` buttons
- Status: In Progress
- parent -> SCR-028

## UI-688: -- (UI-Element)
- Status: In Progress
- parent -> SCR-028

## UI-689: *Type:** Bottom sheet (UI-Element)
drag from 50% → full screen
- Status: In Progress
- parent -> SCR-029

## UI-690: *Triggered from:** SCR-01 Dashboard contextual tip card · SCR-03 Plant Detail contextual tip card · SCR-05 Calculator contextual tip link · SCR-06 Diagnostics results contextual tip link (UI-Element)
- Status: In Progress
- parent -> SCR-029

## UI-691: *Purpose:** Read curated, offline-cached growing guides without leaving the current workflow (UI-Element)
- Status: In Progress
- parent -> SCR-029

## UI-692: *Elements** (UI-Element)
- Status: In Progress
- parent -> SCR-029

## UI-693: Sheet drag handle bar (UI-Element)
- Status: In Progress
- parent -> SCR-029

## UI-694: 🔖 Bookmark icon (UI-Element)
top-left, saves article for later reading offline
- Status: In Progress
- parent -> SCR-029

## UI-695: Article header image (UI-Element)
(offline-cached, lazy-loaded from Wi-Fi download)
- Status: In Progress
- parent -> SCR-029

## UI-696: Article title (UI-Element)
(H1)
- Status: In Progress
- parent -> SCR-029

## UI-697: Meta row (UI-Element)
method tag chip · estimated read time label · author name (if Creator Studio guide) · published date
- Status: In Progress
- parent -> SCR-029

## UI-698: Article body (UI-Element)
rich text content (offline-cached), headings, bulleted lists, inline images
- Status: In Progress
- parent -> SCR-029

## UI-699: Related articles (UI-Element)
row (bottom): 2 suggested articles with thumbnails + titles
- Status: In Progress
- parent -> SCR-029

## UI-700: Mark as Read ✓ button (UI-Element)
footer
- Status: In Progress
- parent -> SCR-029

## UI-701: Share Article icon → MOD-12 Export / Share Sheet (UI-Element)
`Share Article` icon → MOD-12 Export / Share Sheet
- Status: In Progress
- parent -> SCR-029

## UI-702: -- (UI-Element)
- Status: In Progress
- parent -> SCR-029

## UI-703: *Type:** Bottom sheet (UI-Element)
large
- Status: In Progress
- parent -> SCR-030

## UI-704: *Triggered from:** SCR-12 Settings (Notifications row) · SCR-07 Smart Scheduler "Notification preferences →" link (UI-Element)
- Status: In Progress
- parent -> SCR-030

## UI-705: *Purpose:** Granular control over all app notifications in one place (UI-Element)
- Status: In Progress
- parent -> SCR-030

## UI-706: *Elements** (UI-Element)
- Status: In Progress
- parent -> SCR-030

## UI-707: Sheet drag handle bar (UI-Element)
- Status: In Progress
- parent -> SCR-030

## UI-708: "Notification Preferences" heading (UI-Element)
- Status: In Progress
- parent -> SCR-030

## UI-709: 💧 Watering reminders (UI-Element)
- Status: In Progress
- parent -> SCR-030

## UI-710: 🧪 Feeding reminders (UI-Element)
- Status: In Progress
- parent -> SCR-030

## UI-711: 🐛 Pest and disease alerts (UI-Element)
- Status: In Progress
- parent -> SCR-030

## UI-712: 🌦 Weather-based care updates (UI-Element)
- Status: In Progress
- parent -> SCR-030

## UI-713: 👥 Community activity (UI-Element)
clusters, challenges
- Status: In Progress
- parent -> SCR-030

## UI-714: 📊 Weekly Bloom Report (UI-Element)
- Status: In Progress
- parent -> SCR-030

## UI-715: Timing preference section (UI-Element)
- Status: In Progress
- parent -> SCR-030

## UI-716: "I prefer reminders in the:" radio selector: Morning (UI-Element)
7–9 AM) · Afternoon (12–2 PM) · Evening (6–8 PM
- Status: In Progress
- parent -> SCR-030

## UI-717: Travel Mode section (UI-Element)
- Status: In Progress
- parent -> SCR-030

## UI-718: Cancel text link (UI-Element)
below CTA
- Status: In Progress
- parent -> SCR-030

## UI-719: -- (UI-Element)
- Status: In Progress
- parent -> SCR-030

## UI-720: *Type:** Bottom sheet (UI-Element)
large, ~85% screen height
- Status: In Progress
- parent -> SCR-031

## UI-721: *Triggered from:** SCR-01 Dashboard Weekly Bloom Report banner · Push notification tap (UI-Element)
sent Monday mornings
- Status: In Progress
- parent -> SCR-031

## UI-722: *Purpose:** Personalised weekly summary of garden progress, weather correlation, and next-week tips (UI-Element)
- Status: In Progress
- parent -> SCR-031

## UI-723: *Elements** (UI-Element)
- Status: In Progress
- parent -> SCR-031

## UI-724: Sheet drag handle bar (UI-Element)
- Status: In Progress
- parent -> SCR-031

## UI-725: "Your Week in Review 📊" heading (UI-Element)
- Status: In Progress
- parent -> SCR-031

## UI-726: Date range label (UI-Element)
e.g., "May 26 – Jun 1, 2026"
- Status: In Progress
- parent -> SCR-031

## UI-727: Summary stats row (UI-Element)
(4 pill cards, horizontal):
- Status: In Progress
- parent -> SCR-031

## UI-728: Plants logged count (UI-Element)
this week
- Status: In Progress
- parent -> SCR-031

## UI-729: Log entries total (UI-Element)
this week
- Status: In Progress
- parent -> SCR-031

## UI-730: Health Score change (UI-Element)
e.g., "+7 pts"
- Status: In Progress
- parent -> SCR-031

## UI-731: Streak status (UI-Element)
e.g., "🔥 14 days"
- Status: In Progress
- parent -> SCR-031

## UI-732: Star performer card (UI-Element)
"Best performing plant this week" — plant thumbnail, plant name, method badge, health improvement label
- Status: In Progress
- parent -> SCR-031

## UI-733: Weather correlation insight (UI-Element)
e.g., "Your tomatoes thrived during the 3 sunny days this week — more sun exposure correlates with better growth"
- Status: In Progress
- parent -> SCR-031

## UI-734: Cemetery alert (UI-Element)
(conditional — shown if a plant was archived this week): "⚠ 1 plant archived this week → See Cemetery Log" link → SCR-14
- Status: In Progress
- parent -> SCR-031

## UI-735: Next week tip card (UI-Element)
contextual tip based on upcoming forecast and planting zone (e.g., "Frost risk Friday → bring indoor plants in by Thursday night")
- Status: In Progress
- parent -> SCR-031

## UI-736: Share Report icon button → MOD-12 Export / Share Sheet (UI-Element)
`Share Report` icon button → MOD-12 Export / Share Sheet
- Status: In Progress
- parent -> SCR-031

## UI-737: View Full Garden → CTA button → SCR-02 Plant List (UI-Element)
`View Full Garden →` CTA button → SCR-02 Plant List
- Status: In Progress
- parent -> SCR-031

## UI-738: Dismiss text link (UI-Element)
footer
- Status: In Progress
- parent -> SCR-031

## UI-739: -- (UI-Element)
- Status: In Progress
- parent -> SCR-031

## UI-740: *Type:** GardenPulse pre-share layer (bottom sheet) followed by native OS share sheet (UI-Element)
- Status: In Progress
- parent -> SCR-032

## UI-741: *Triggered from:** SCR-03 Plant Detail Share pill · SCR-05 Calculator (after rewarded video unlock) · SCR-09 Cluster Detail overflow share · SCR-11 Profile referral Share Invite Link · SCR-14 Cemetery Log export · SCR-15 Reels Share button · SCR-08 Community Hub referral Share Invite Link · MOD-05 Rewarded Video success state · MOD-09 Tip Article Share Article icon · MOD-11 Bloom Report Share Report icon (UI-Element)
*Triggered from:** SCR-03 Plant Detail `Share` pill · SCR-05 Calculator (after rewarded video unlock) · SCR-09 Cluster Detail overflow share · SCR-11 Profile referral `Share Invite Link` · SCR-14 Cemetery Log export · SCR-15 Reels `Share` button · SCR-08 Community Hub referral `Share Invite Link` · MOD-05 Rewarded Video success state · MOD-09 Tip Article `Share Article` icon · MOD-11 Bloom Report `Share Report` icon
- Status: In Progress
- parent -> SCR-032

## UI-742: *Purpose:** Export and share content across platforms with brand-appropriate formatting (UI-Element)
- Status: In Progress
- parent -> SCR-032

## UI-743: *GardenPulse Pre-Share Layer** (shown first, before OS share sheet): (UI-Element)
- Status: In Progress
- parent -> SCR-032

## UI-744: Content preview thumbnail (UI-Element)
photo / PDF preview / reel frame, contextually appropriate
- Status: In Progress
- parent -> SCR-032

## UI-745: Format options (UI-Element)
(shown contextually per content type):
- Status: In Progress
- parent -> SCR-032

## UI-746: 📷 Share as Image (PNG) — always available (UI-Element)
`📷 Share as Image (PNG)` — always available
- Status: In Progress
- parent -> SCR-032

## UI-747: 📄 Export PDF — available after rewarded video unlock (MOD-05); greys out and shows "Watch video to unlock" if not yet unlocked (UI-Element)
`📄 Export PDF` — available after rewarded video unlock (MOD-05); greys out and shows "Watch video to unlock" if not yet unlocked
- Status: In Progress
- parent -> SCR-032

## UI-748: 📋 Copy Text Summary — plain text version (UI-Element)
`📋 Copy Text Summary` — plain text version
- Status: In Progress
- parent -> SCR-032

## UI-749: Continue to Share → button → fires native OS share sheet (UI-Element)
`Continue to Share →` button → fires native OS share sheet
- Status: In Progress
- parent -> SCR-032

## UI-750: *Native OS Share Sheet** (system-level, appears after Continue to Share →): (UI-Element)
*Native OS Share Sheet** (system-level, appears after `Continue to Share →`):
- Status: In Progress
- parent -> SCR-032

## UI-751: Platform icons: Instagram · TikTok · WhatsApp · Messages · Copy Link · Save to Photos · More (UI-Element)
- Status: In Progress
- parent -> SCR-032

## UI-752: System Cancel button (UI-Element)
- Status: In Progress
- parent -> SCR-032
